METASWITCH-OS-MIB DEFINITIONS ::= BEGIN

IMPORTS
        MODULE-IDENTITY, OBJECT-TYPE, Integer32 FROM SNMPv2-SMI
        OBJECT-GROUP FROM SNMPv2-CONF;

-- Module definition

  os   MODULE-IDENTITY
        LAST-UPDATED "201801281022Z"
        ORGANIZATION "Metaswitch"
        CONTACT-INFO
          "Metaswitch
           100 Church Street
           Enfield
           EN2 6BQ
           United Kingdom
           Tel: +44 20 8366 1177"
        DESCRIPTION  "This MIB module defines OS statistics MIBs"

        REVISION     "201801281022Z" -- 25 Jan 2018
        DESCRIPTION  "Addition of memory fields"

        REVISION     "201801250900Z"  -- 28 Jan 2018
        DESCRIPTION  "Creation of the MIB"

        ::= { dataConnection 17 }

-- The object identifier subtree for the Metaswitch OS MIBs.

memberBody      OBJECT IDENTIFIER ::= { iso 2 }
gb              OBJECT IDENTIFIER ::= { memberBody 826 }
gbNational      OBJECT IDENTIFIER ::= { gb 0 }
gbNatCompany    OBJECT IDENTIFIER ::= { gbNational 1 }
dataConnection  OBJECT IDENTIFIER ::= { gbNatCompany 1578918 }

-- OS Entries

fileDescriptors OBJECT IDENTIFIER ::= { os 1 }

osFileDescriptorsCurrent OBJECT-TYPE
    SYNTAX      Integer32
    MAX-ACCESS  read-only
    STATUS      current
    DESCRIPTION "Current number of file descriptors in use."
    ::= { fileDescriptors 1 }

osFileDescriptorsMax OBJECT-TYPE
    SYNTAX      Integer32
    MAX-ACCESS  read-only
    STATUS      current
    DESCRIPTION "Maximum number of file descriptors that OS guarantees to have
                 available."
    ::= { fileDescriptors 2 }

osFileDescriptorsPercent OBJECT-TYPE
    SYNTAX      Integer32
    MAX-ACCESS  read-only
    STATUS      current
    DESCRIPTION "Current percentage of file descriptors in use."
    ::= { fileDescriptors 3 }


osMemory OBJECT IDENTIFIER ::= { os 2 }

osMemoryRealFreeCurrent OBJECT-TYPE
    SYNTAX      Integer32
    MAX-ACCESS  read-only
    STATUS      current
    DESCRIPTION "Current free memory on this node (including buffers and cached)."
    ::= { osMemory 1 }

osMemoryRealMax OBJECT-TYPE
    SYNTAX      Integer32
    MAX-ACCESS  read-only
    STATUS      current
    DESCRIPTION "Maximum available memory on this node."
    ::= { osMemory 2 }

osMemoryRealFreePercent OBJECT-TYPE
    SYNTAX      Integer32
    MAX-ACCESS  read-only
    STATUS      current
    DESCRIPTION "Current percentage of free memory on this node."
    ::= { osMemory 3 }

-- End of OS MIB entries

END
