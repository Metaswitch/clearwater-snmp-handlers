CLEARWATER-ENTERPRISE-MIB DEFINITIONS ::= BEGIN

IMPORTS
        MODULE-IDENTITY, OBJECT-TYPE, enterprises,
        NOTIFICATION-TYPE
                                            FROM SNMPv2-SMI
        DisplayString
                                            FROM SNMPv2-TC
        OBJECT-GROUP, MODULE-COMPLIANCE, NOTIFICATION-GROUP
                                            FROM SNMPv2-CONF;


  clearwater MODULE-IDENTITY
        LAST-UPDATED "201608081100Z"
        ORGANIZATION "MetaSwitch"
        CONTACT-INFO
          "MetaSwitch
           100 Church Street
           Enfield
           EN2 6BQ
           United Kingdom
           Tel: +44 20 8366 1177"
        DESCRIPTION  "This MIB defines the Enterprise MIBs generated
                      by Clearwater-snmp-handlers"
        
        REVISION     "201608081100Z" -- 08 August 2016
        DESCRIPTION  "Creation of the MIB"

 
        ::= { dataConnection 12 }


-- /**********************************************************/
-- /* The object identifier subtree for the Clearwater MIBs. */
-- /**********************************************************/

memberBody      OBJECT IDENTIFIER ::= { iso 2 }
gb              OBJECT IDENTIFIER ::= { memberBody 826 }
gbNational      OBJECT IDENTIFIER ::= { gb 0 }
gbNatCompany    OBJECT IDENTIFIER ::= { gbNational 1 }
dataConnection  OBJECT IDENTIFIER ::= { gbNatCompany 1578918 }
dataConnectionTraps  OBJECT IDENTIFIER ::= { enterprises 19444 }
clearwaterEMS  OBJECT IDENTIFIER ::= { dataConnectionTraps 12 }

-- Module Compliance
clearwaterEnterpriseMIBConformance OBJECT IDENTIFIER ::= { clearwater 0}
clearwaterEnterpriseMIBCompliance MODULE-COMPLIANCE
  STATUS current
  DESCRIPTION "Compliance statement for Clearwater-Enterprise-MIB"
  MODULE
  GROUP alarmTrapGroup
  DESCRIPTION "Makes the module aware of the alarmTrapGroup"
  ::= { clearwaterEnterpriseMIBConformance 1 }
clearwaterEnterpriseMIBCompliance2 MODULE-COMPLIANCE
  STATUS current
  DESCRIPTION "Compliance statement for Clearwater-Enterprise-MIB"
  MODULE
  GROUP alarmGroup
  DESCRIPTION "Makes the module aware of the alarmGroup"
  ::= { clearwaterEnterpriseMIBConformance 2 }

-- /*********************************************************/
-- /* MIB Info Section                                      */
-- /*********************************************************/

clearwaterInfo  OBJECT IDENTIFIER ::= { clearwater 1 }

  clearwaterInfoVersion OBJECT-TYPE
    SYNTAX       DisplayString
    MAX-ACCESS   read-only
    STATUS       current
    DESCRIPTION  "Clearwater MIB Version"
    ::= { clearwaterInfo 1 }

-- /*********************************************************/
-- /* Traps section                                         */
-- /*********************************************************/

clearwaterTraps OBJECT IDENTIFIER ::= { clearwaterEMS 2 }

  alarmGroup NOTIFICATION-GROUP
    NOTIFICATIONS     { alarmTrap
                        }
    STATUS            current
    DESCRIPTION       "For syntactic reasons each NOTIFICATION must belong to a
                       group"
    ::= { clearwaterTraps 1 }
  

-- /**************************************************************************/
-- /* Trap for Clearwater alarms.                                            */
-- /**************************************************************************/
alarmTrapsPrefix OBJECT IDENTIFIER ::= { clearwaterTraps 0 }

  alarmTrapGroup OBJECT-GROUP
    OBJECTS      { clearwaterInfoVersion,
                   alarmTrapDisplayName,
                   alarmTrapAlarmOID,
                   alarmTrapResourceID,
                   alarmTrapSeverity,
                   alarmTrapDescription,
                   alarmTrapDetails,
                   alarmTrapCause,
                   alarmTrapEffect,
                   alarmTrapAction,
                   alarmTrapHostname
                   }
    STATUS       current
    DESCRIPTION  "A collection of objects providing information about the
                  instance of an alarm"
    ::= { alarmTrapsPrefix 11 }

  alarmTrap NOTIFICATION-TYPE
    OBJECTS      { alarmTrapDisplayName,
                   alarmTrapAlarmOID,
                   alarmTrapResourceID,
                   alarmTrapSeverity,
                   alarmTrapDescription,
                   alarmTrapDetails,
                   alarmTrapCause,
                   alarmTrapEffect,
                   alarmTrapAction,
                   alarmTrapHostname
                   }
    STATUS       current
    DESCRIPTION  "This is the alarm trap table for Clearwater.  A
                  notify is sent on this table when a Clearwater
                  object is either alarmed or cleared.  Logs associated
                  with the alarmed object are supplied in the
                  Description, Details, Cause, Effect and Action fields. "
    ::= { alarmTrapsPrefix 1 } 

  alarmTrapDisplayName OBJECT-TYPE
    SYNTAX       DisplayString (SIZE (1..128))
    MAX-ACCESS   read-write
    STATUS       current
    DESCRIPTION  "The user-friendly display name of the alarmed element"
    ::= { alarmTrapsPrefix 2 }

  alarmTrapAlarmOID OBJECT-TYPE
    SYNTAX       OBJECT IDENTIFIER 
    MAX-ACCESS   read-write
    STATUS       current
    DESCRIPTION  "The OID of the alarm.  Gets and Sets on
                  this OID are supported. "
    ::= { alarmTrapsPrefix 3 }

  alarmTrapResourceID OBJECT-TYPE
    SYNTAX       OBJECT IDENTIFIER
    MAX-ACCESS   read-write
    STATUS       current
    DESCRIPTION  "Resource ID."
    ::= { alarmTrapsPrefix 4 }

  alarmTrapSeverity OBJECT-TYPE
    SYNTAX       DisplayString (SIZE (1..4096))
    MAX-ACCESS   read-write
    STATUS       current
    DESCRIPTION  "Severity"
    ::= { alarmTrapsPrefix 5 }

  alarmTrapDescription OBJECT-TYPE
    SYNTAX       DisplayString (SIZE (1..4096))
    MAX-ACCESS   read-write
    STATUS       current
    DESCRIPTION  "Detailed description of the alarmed condition."
    ::= { alarmTrapsPrefix 6 }

  alarmTrapDetails OBJECT-TYPE
    SYNTAX       DisplayString (SIZE (1..4096))
    MAX-ACCESS   read-write
    STATUS       current
    DESCRIPTION  "Details about the alarmed condition."
    ::= { alarmTrapsPrefix 7 }

  alarmTrapCause OBJECT-TYPE
    SYNTAX       DisplayString (SIZE (1..4096))
    MAX-ACCESS   read-write
    STATUS       current
    DESCRIPTION  "Information on possible causes of the alarmed condition."
    ::= { alarmTrapsPrefix 8 }

  alarmTrapEffect OBJECT-TYPE
    SYNTAX       DisplayString (SIZE (1..4096))
    MAX-ACCESS   read-write
    STATUS       current
    DESCRIPTION  "Information on other events that may occur as a
                  result of the alarmed condition."
    ::= { alarmTrapsPrefix 9 }

  alarmTrapAction OBJECT-TYPE
    SYNTAX       DisplayString (SIZE (1..4096))
    MAX-ACCESS   read-write
    STATUS       current
    DESCRIPTION  "Suggested actions that you can take to resolve the problem."
    ::= { alarmTrapsPrefix 10 }

  -- alarmTrapsPrefix 11 is used for alarmTrapGroup above

  alarmTrapHostname OBJECT-TYPE
    SYNTAX       DisplayString (SIZE (1..4096))
    MAX-ACCESS   read-write
    STATUS       current
    DESCRIPTION  "Hostname of the network element raising this alarm."
    ::= { alarmTrapsPrefix 12 }

END
