METASWITCH-OS-MIB DEFINITIONS ::= BEGIN

IMPORTS
        MODULE-IDENTITY, OBJECT-TYPE, Unsigned32 FROM SNMPv2-SMI
        OBJECT-GROUP FROM SNMPv2-CONF;

-- Module definition

  os   MODULE-IDENTITY
        LAST-UPDATED "201801250900Z"
        ORGANIZATION "Metaswitch"
        CONTACT-INFO
          "Metaswitch
           100 Church Street
           Enfield
           EN2 6BQ
           United Kingdom
           Tel: +44 20 8366 1177"
        DESCRIPTION  "This MIB module defines OS statistics MIBs"

        ::= { dataConnection 17 }

-- The object identifier subtree for the Metaswitch OS MIBs.

memberBody      OBJECT IDENTIFIER ::= { iso 2 }
gb              OBJECT IDENTIFIER ::= { memberBody 826 }
gbNational      OBJECT IDENTIFIER ::= { gb 0 }
gbNatCompany    OBJECT IDENTIFIER ::= { gbNational 1 }
dataConnection  OBJECT IDENTIFIER ::= { gbNatCompany 1578918 }

-- OS Entries

osFileDescriptorsCurrent OBJECT-TYPE
    SYNTAX      Integer32
    MAX-ACCESS  read-only
    STATUS      current
    DESCRIPTION "Current number of file descriptors in use."
    ::= { fileDescriptors 1 }

osFileDescriptorsMax OBJECT-TYPE
    SYNTAX      Integer32
    MAX-ACCESS  read-only
    STATUS      current
    DESCRIPTION "Maximum number of file descriptors that OS guarantees to have
                 available."
    ::= { fileDescriptors 2 }

osFileDescriptorsPercent OBJECT-TYPE
    SYNTAX      Integer32
    MAX-ACCESS  read-only
    STATUS      current
    DESCRIPTION "Current percentage of file descriptors in use."
    ::= { fileDescriptors 3 }


fileDescriptors OBJECT-GROUP
    OBJECTS {
        osFileDescriptorsCurrent,
        osFileDescriptorsMax,
        osFileDescriptorsPercent
    }
    STATUS      current
    DESCRIPTION "File Descriptor statistics"
    ::= { os 1 }

-- End of OS MIB entries

END
