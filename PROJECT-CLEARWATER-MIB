PROJECT-CLEARWATER-MIB DEFINITIONS ::= BEGIN

-- THIS MIB IS BUILT FROM A TEMPLATE - DO NOT EDIT DIRECTLY!

IMPORTS
        MODULE-IDENTITY, OBJECT-TYPE, Unsigned32 FROM SNMPv2-SMI
        MODULE-COMPLIANCE, OBJECT-GROUP FROM SNMPv2-CONF
        InetAddressType, InetAddress FROM INET-ADDRESS-MIB
        TEXTUAL-CONVENTION FROM SNMPv2-TC;

-- Module definition

  projectClearwater MODULE-IDENTITY
        LAST-UPDATED "201705310000Z"
        ORGANIZATION "Metaswitch"
        CONTACT-INFO
          "Metaswitch
           100 Church Street
           Enfield
           EN2 6BQ
           United Kingdom
           Tel: +44 20 8366 1177"
        DESCRIPTION  "This MIB module defines the Project
                      Clearwater statistics MIBs"

        REVISION      "201705310000Z" -- 31 May 2017
        DESCRIPTION   "Auto-generation update for PC and CWC MIBs"

        REVISION      "201510070000Z" -- 07 Oct 2015
        DESCRIPTION   "Fix warning messages about naming conventions"

        REVISION      "201506220000Z" -- 22 Jun 2015
        DESCRIPTION   "Additional time scopes for Sprout/Bono stats"

        REVISION      "201411180000Z" -- 18 Nov 2014
        DESCRIPTION   "Addition of Memento statistics"

        REVISION      "201310102120Z" -- 10 Oct 2013
        DESCRIPTION   "Registration of initial global statistics"

        ::= { dataConnection 9 }

-- The object identifier subtree for the ProjectClearwater MIBs.

memberBody      OBJECT IDENTIFIER ::= { iso 2 }
gb              OBJECT IDENTIFIER ::= { memberBody 826 }
gbNational      OBJECT IDENTIFIER ::= { gb 0 }
gbNatCompany    OBJECT IDENTIFIER ::= { gbNational 1 }
dataConnection  OBJECT IDENTIFIER ::= { gbNatCompany 1578918 }

-- Additional Clearwater Core identifiers.

houdini         OBJECT IDENTIFIER ::= { dataConnection 13 }
weatherwax      OBJECT IDENTIFIER ::= { dataConnection 14 }

-- Common Clearwater Module Compliance
commonClearwaterConformance OBJECT IDENTIFIER ::= { projectClearwater 0 }
commonClearwaterCompliance MODULE-COMPLIANCE
    STATUS current
    DESCRIPTION "Compilance statement for components common to both Project
                 Clearwater and Clearwater Core."
    MODULE
    GROUP sproutGroup
    DESCRIPTION "The sproutGroup must be exposed by Sprout nodes"
    GROUP homesteadGroup
    DESCRIPTION "The homesteadGroup must be exposed by Homestead nodes"
    GROUP astaireGroup
    DESCRIPTION "The astaireGroup must be exposed by nodes running Astaire"
    GROUP chronosGroup
    DESCRIPTION "The chronosGroup must be exposed by nodes running Chronos"
    ::= { commonClearwaterConformance 1 }
commonClearwaterObjectGroups OBJECT IDENTIFIER ::= { projectClearwater 1 }

-- Node roles
--
-- Note that ID 0 is used for the module compliance.
-- Note that this lists ALL Clearwater components.
bono             OBJECT IDENTIFIER ::= { projectClearwater 2 }
sprout           OBJECT IDENTIFIER ::= { projectClearwater 3 }
homer            OBJECT IDENTIFIER ::= { projectClearwater 4 }
homestead        OBJECT IDENTIFIER ::= { projectClearwater 5 }
sipp             OBJECT IDENTIFIER ::= { projectClearwater 6 }
callDiversionAs  OBJECT IDENTIFIER ::= { projectClearwater 7 }
memento          OBJECT IDENTIFIER ::= { projectClearwater 8 }
astaire          OBJECT IDENTIFIER ::= { projectClearwater 9 }
chronos          OBJECT IDENTIFIER ::= { projectClearwater 10 }
gemini           OBJECT IDENTIFIER ::= { projectClearwater 11 }
weatherwaxNode   OBJECT IDENTIFIER ::= { weatherwax 2 }
bgcf             OBJECT IDENTIFIER ::= { houdini 2 }

RequestType ::= TEXTUAL-CONVENTION
    STATUS      current
    DESCRIPTION "Represents a type of SIP request."
    SYNTAX      INTEGER {
                scopeINVITE(0),
                scopeACK(1),
                scopeBYE(2),
                scopeCANCEL(3),
                scopeOPTIONS(4),
                scopeREGISTER(5),
                scopePRACK(6),
                scopeSUBSCRIBE(7),
                scopeNOTIFY(8),
                scopePUBLISH(9),
                scopeINFO(10),
                scopeREFER(11),
                scopeMESSAGE(12),
                scopeUPDATE(13),
                scopeOTHER(14)
                }

-- Sprout entries

sproutLatencyTable OBJECT-TYPE
    SYNTAX SEQUENCE OF SproutLatencyEntry
    MAX-ACCESS not-accessible
    STATUS current
    DESCRIPTION "Latency of SIP requests handled by this Sprout
                 over the given period.  Latency measured in
                 microseconds"
    ::= { sprout 1 }

sproutLatencyEntry OBJECT-TYPE
    SYNTAX      SproutLatencyEntry
    MAX-ACCESS  not-accessible
    STATUS      current
    DESCRIPTION "The average, variance, LWM and HWM of SIP message
                 latency"
    INDEX       { sproutLatencyTimeFrame,
                  sproutLatencyScope }
    ::= { sproutLatencyTable 1 }

SproutLatencyEntry ::= SEQUENCE
{
  sproutLatencyTimeFrame      INTEGER,
  sproutLatencyScope          OCTET STRING,
  sproutLatencyAverage        Unsigned32,
  sproutLatencyVariance       Unsigned32,
  sproutLatencyHWM            Unsigned32,
  sproutLatencyLWM            Unsigned32,
  sproutLatencyCount          Unsigned32
}

sproutLatencyTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutLatencyEntry 1 }

sproutLatencyScope OBJECT-TYPE
    SYNTAX      OCTET STRING (SIZE(1..64))
    MAX-ACCESS  not-accessible
    STATUS      current
    DESCRIPTION "Statistic scope - should always take the value: node."
    ::= { sproutLatencyEntry 2 }

sproutLatencyAverage OBJECT-TYPE
    SYNTAX      Unsigned32
    MAX-ACCESS  read-only
    STATUS      current
    DESCRIPTION "The average latency over the period."
    ::= { sproutLatencyEntry 3 }

sproutLatencyVariance OBJECT-TYPE
    SYNTAX      Unsigned32
    MAX-ACCESS  read-only
    STATUS      current
    DESCRIPTION "The variance of the latency over the period."
    ::= { sproutLatencyEntry 4 }

sproutLatencyHWM OBJECT-TYPE
    SYNTAX      Unsigned32
    MAX-ACCESS  read-only
    STATUS      current
    DESCRIPTION "The highest latency over the period."
    ::= { sproutLatencyEntry 5 }

sproutLatencyLWM OBJECT-TYPE
    SYNTAX      Unsigned32
    MAX-ACCESS  read-only
    STATUS      current
    DESCRIPTION "The lowest latency over the period."
    ::= { sproutLatencyEntry 6 }

sproutLatencyCount OBJECT-TYPE
    SYNTAX      Unsigned32
    MAX-ACCESS  read-only
    STATUS      current
    DESCRIPTION "The total requests over the period."
    ::= { sproutLatencyEntry 7 }

hss OBJECT IDENTIFIER ::= { sprout 3 }

sproutConnectedHomesteadsTable OBJECT-TYPE
    SYNTAX SEQUENCE OF SproutConnectedHomesteadsEntry
    MAX-ACCESS not-accessible
    STATUS current
    DESCRIPTION "Statistics for each connected upstream Homestead node"
    ::= { hss 1 }

sproutConnectedHomesteadsEntry OBJECT-TYPE
    SYNTAX SproutConnectedHomesteadsEntry
    MAX-ACCESS not-accessible
    STATUS current
    DESCRIPTION "Statistics for a single connected upstream Homestead"
    INDEX { sproutHomesteadInetAddrType,
            sproutHomesteadInetAddr      }
    ::= { sproutConnectedHomesteadsTable 1 }

SproutConnectedHomesteadsEntry ::= SEQUENCE
{
  sproutHomesteadInetAddrType    InetAddressType,
  sproutHomesteadInetAddr        InetAddress,
  sproutHomesteadConnectionCount Unsigned32
}

sproutHomesteadInetAddrType OBJECT-TYPE
    SYNTAX      InetAddressType
    MAX-ACCESS  not-accessible
    STATUS      current
    DESCRIPTION "Inet address type of the upstream Homestead"
    ::= { sproutConnectedHomesteadsEntry 1 }

sproutHomesteadInetAddr OBJECT-TYPE
    SYNTAX      InetAddress (SIZE (1..16))
    MAX-ACCESS  not-accessible
    STATUS      current
    DESCRIPTION "Inet address of the upstream Homestead"
    ::= { sproutConnectedHomesteadsEntry 2 }

sproutHomesteadConnectionCount OBJECT-TYPE
    SYNTAX      Unsigned32
    MAX-ACCESS  read-only
    STATUS      current
    DESCRIPTION "Current count of TCP connections from Sprout to the
                 Homestead node, may include connections in setting-
                 up state"
    ::= { sproutConnectedHomesteadsEntry 3 }

sproutHomesteadLatencyTable OBJECT-TYPE
    SYNTAX SEQUENCE OF SproutHomesteadLatencyEntry
    MAX-ACCESS not-accessible
    STATUS current
    DESCRIPTION "Latency of Homestead requests made by this Sprout
                 over a the given period.  Latency measured in
                 microseconds"
    ::= { hss 2 }

sproutHomesteadLatencyEntry OBJECT-TYPE
    SYNTAX      SproutHomesteadLatencyEntry
    MAX-ACCESS  not-accessible
    STATUS      current
    DESCRIPTION "The average, variance, LWM and HWM of request
                 latency"
    INDEX       { sproutHomesteadLatencyScope }
    ::= { sproutHomesteadLatencyTable 1 }

SproutHomesteadLatencyEntry ::= SEQUENCE
{
  sproutHomesteadLatencyScope          INTEGER,
  sproutHomesteadLatencyAverage        Unsigned32,
  sproutHomesteadLatencyVariance       Unsigned32,
  sproutHomesteadLatencyHWM            Unsigned32,
  sproutHomesteadLatencyLWM            Unsigned32,
  sproutHomesteadLatencyCount          Unsigned32
}

sproutHomesteadLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutHomesteadLatencyEntry 1 }

sproutHomesteadLatencyAverage OBJECT-TYPE
    SYNTAX      Unsigned32
    MAX-ACCESS  read-only
    STATUS      current
    DESCRIPTION "The average latency over the period."
    ::= { sproutHomesteadLatencyEntry 2 }

sproutHomesteadLatencyVariance OBJECT-TYPE
    SYNTAX      Unsigned32
    MAX-ACCESS  read-only
    STATUS      current
    DESCRIPTION "The variance of the latency over the period."
    ::= { sproutHomesteadLatencyEntry 3 }

sproutHomesteadLatencyHWM OBJECT-TYPE
    SYNTAX      Unsigned32
    MAX-ACCESS  read-only
    STATUS      current
    DESCRIPTION "The highest latency over the period."
    ::= { sproutHomesteadLatencyEntry 4 }

sproutHomesteadLatencyLWM OBJECT-TYPE
    SYNTAX      Unsigned32
    MAX-ACCESS  read-only
    STATUS      current
    DESCRIPTION "The lowest latency over the period."
    ::= { sproutHomesteadLatencyEntry 5 }

sproutHomesteadLatencyCount OBJECT-TYPE
    SYNTAX      Unsigned32
    MAX-ACCESS  read-only
    STATUS      current
    DESCRIPTION "The total requests over the period."
    ::= { sproutHomesteadLatencyEntry 6 }

sproutMARLatencyTable OBJECT-TYPE
    SYNTAX SEQUENCE OF SproutMARLatencyEntry
    MAX-ACCESS not-accessible
    STATUS current
    DESCRIPTION "Latency of requests for MARs made by this Sprout
                 over the given period.  Latency measured in
                 microseconds"
    ::= { hss 3 }

sproutMARLatencyEntry OBJECT-TYPE
    SYNTAX      SproutMARLatencyEntry
    MAX-ACCESS  not-accessible
    STATUS      current
    DESCRIPTION "The average, variance, LWM and HWM of request
                 latency"
    INDEX       { sproutMARLatencyScope }
    ::= { sproutMARLatencyTable 1 }

SproutMARLatencyEntry ::= SEQUENCE
{
  sproutMARLatencyScope          INTEGER,
  sproutMARLatencyAverage        Unsigned32,
  sproutMARLatencyVariance       Unsigned32,
  sproutMARLatencyHWM            Unsigned32,
  sproutMARLatencyLWM            Unsigned32,
  sproutMARLatencyCount          Unsigned32
}

sproutMARLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutMARLatencyEntry 1 }

sproutMARLatencyAverage OBJECT-TYPE
    SYNTAX      Unsigned32
    MAX-ACCESS  read-only
    STATUS      current
    DESCRIPTION "The average latency over the period."
    ::= { sproutMARLatencyEntry 2 }

sproutMARLatencyVariance OBJECT-TYPE
    SYNTAX      Unsigned32
    MAX-ACCESS  read-only
    STATUS      current
    DESCRIPTION "The variance of the latency over the period."
    ::= { sproutMARLatencyEntry 3 }

sproutMARLatencyHWM OBJECT-TYPE
    SYNTAX      Unsigned32
    MAX-ACCESS  read-only
    STATUS      current
    DESCRIPTION "The highest latency over the period."
    ::= { sproutMARLatencyEntry 4 }

sproutMARLatencyLWM OBJECT-TYPE
    SYNTAX      Unsigned32
    MAX-ACCESS  read-only
    STATUS      current
    DESCRIPTION "The lowest latency over the period."
    ::= { sproutMARLatencyEntry 5 }

sproutMARLatencyCount OBJECT-TYPE
    SYNTAX      Unsigned32
    MAX-ACCESS  read-only
    STATUS      current
    DESCRIPTION "The total requests over the period."
    ::= { sproutMARLatencyEntry 6 }

sproutSARLatencyTable OBJECT-TYPE
    SYNTAX SEQUENCE OF SproutSARLatencyEntry
    MAX-ACCESS not-accessible
    STATUS current
    DESCRIPTION "Latency of requests for SARs made by this Sprout
                 over the given period.  Latency measured in
                 microseconds"
    ::= { hss 4 }

sproutSARLatencyEntry OBJECT-TYPE
    SYNTAX      SproutSARLatencyEntry
    MAX-ACCESS  not-accessible
    STATUS      current
    DESCRIPTION "The average, variance, LWM and HWM of request
                 latency"
    INDEX       { sproutSARLatencyScope }
    ::= { sproutSARLatencyTable 1 }

SproutSARLatencyEntry ::= SEQUENCE
{
  sproutSARLatencyScope          INTEGER,
  sproutSARLatencyAverage        Unsigned32,
  sproutSARLatencyVariance       Unsigned32,
  sproutSARLatencyHWM            Unsigned32,
  sproutSARLatencyLWM            Unsigned32,
  sproutSARLatencyCount          Unsigned32
}

sproutSARLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSARLatencyEntry 1 }

sproutSARLatencyAverage OBJECT-TYPE
    SYNTAX      Unsigned32
    MAX-ACCESS  read-only
    STATUS      current
    DESCRIPTION "The average latency over the period."
    ::= { sproutSARLatencyEntry 2 }

sproutSARLatencyVariance OBJECT-TYPE
    SYNTAX      Unsigned32
    MAX-ACCESS  read-only
    STATUS      current
    DESCRIPTION "The variance of the latency over the period."
    ::= { sproutSARLatencyEntry 3 }

sproutSARLatencyHWM OBJECT-TYPE
    SYNTAX      Unsigned32
    MAX-ACCESS  read-only
    STATUS      current
    DESCRIPTION "The highest latency over the period."
    ::= { sproutSARLatencyEntry 4 }

sproutSARLatencyLWM OBJECT-TYPE
    SYNTAX      Unsigned32
    MAX-ACCESS  read-only
    STATUS      current
    DESCRIPTION "The lowest latency over the period."
    ::= { sproutSARLatencyEntry 5 }

sproutSARLatencyCount OBJECT-TYPE
    SYNTAX      Unsigned32
    MAX-ACCESS  read-only
    STATUS      current
    DESCRIPTION "The total requests over the period."
    ::= { sproutSARLatencyEntry 6 }

sproutUARLatencyTable OBJECT-TYPE
    SYNTAX SEQUENCE OF SproutUARLatencyEntry
    MAX-ACCESS not-accessible
    STATUS current
    DESCRIPTION "Latency of requests for user authentication made by this Sprout
                 over the given period.  Latency measured in
                 microseconds"
    ::= { hss 5 }

sproutUARLatencyEntry OBJECT-TYPE
    SYNTAX      SproutUARLatencyEntry
    MAX-ACCESS  not-accessible
    STATUS      current
    DESCRIPTION "The average, variance, LWM and HWM of request
                 latency"
    INDEX       { sproutUARLatencyScope }
    ::= { sproutUARLatencyTable 1 }

SproutUARLatencyEntry ::= SEQUENCE
{
  sproutUARLatencyScope          INTEGER,
  sproutUARLatencyAverage        Unsigned32,
  sproutUARLatencyVariance       Unsigned32,
  sproutUARLatencyHWM            Unsigned32,
  sproutUARLatencyLWM            Unsigned32,
  sproutUARLatencyCount          Unsigned32
}

sproutUARLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutUARLatencyEntry 1 }

sproutUARLatencyAverage OBJECT-TYPE
    SYNTAX      Unsigned32
    MAX-ACCESS  read-only
    STATUS      current
    DESCRIPTION "The average latency over the period."
    ::= { sproutUARLatencyEntry 2 }

sproutUARLatencyVariance OBJECT-TYPE
    SYNTAX      Unsigned32
    MAX-ACCESS  read-only
    STATUS      current
    DESCRIPTION "The variance of the latency over the period."
    ::= { sproutUARLatencyEntry 3 }

sproutUARLatencyHWM OBJECT-TYPE
    SYNTAX      Unsigned32
    MAX-ACCESS  read-only
    STATUS      current
    DESCRIPTION "The highest latency over the period."
    ::= { sproutUARLatencyEntry 4 }

sproutUARLatencyLWM OBJECT-TYPE
    SYNTAX      Unsigned32
    MAX-ACCESS  read-only
    STATUS      current
    DESCRIPTION "The lowest latency over the period."
    ::= { sproutUARLatencyEntry 5 }

sproutUARLatencyCount OBJECT-TYPE
    SYNTAX      Unsigned32
    MAX-ACCESS  read-only
    STATUS      current
    DESCRIPTION "The total requests over the period."
    ::= { sproutUARLatencyEntry 6 }

sproutLIRLatencyTable OBJECT-TYPE
    SYNTAX SEQUENCE OF SproutLIRLatencyEntry
    MAX-ACCESS not-accessible
    STATUS current
    DESCRIPTION "Latency of location requests made by this Sprout
                 over the given period.  Latency measured in
                 microseconds"
    ::= { hss 6 }

sproutLIRLatencyEntry OBJECT-TYPE
    SYNTAX      SproutLIRLatencyEntry
    MAX-ACCESS  not-accessible
    STATUS      current
    DESCRIPTION "The average, variance, LWM and HWM of request
                 latency"
    INDEX       { sproutLIRLatencyScope }
    ::= { sproutLIRLatencyTable 1 }

SproutLIRLatencyEntry ::= SEQUENCE
{
  sproutLIRLatencyScope          INTEGER,
  sproutLIRLatencyAverage        Unsigned32,
  sproutLIRLatencyVariance       Unsigned32,
  sproutLIRLatencyHWM            Unsigned32,
  sproutLIRLatencyLWM            Unsigned32,
  sproutLIRLatencyCount          Unsigned32
}

sproutLIRLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutLIRLatencyEntry 1 }

sproutLIRLatencyAverage OBJECT-TYPE
    SYNTAX      Unsigned32
    MAX-ACCESS  read-only
    STATUS      current
    DESCRIPTION "The average latency over the period."
    ::= { sproutLIRLatencyEntry 2 }

sproutLIRLatencyVariance OBJECT-TYPE
    SYNTAX      Unsigned32
    MAX-ACCESS  read-only
    STATUS      current
    DESCRIPTION "The variance of the latency over the period."
    ::= { sproutLIRLatencyEntry 3 }

sproutLIRLatencyHWM OBJECT-TYPE
    SYNTAX      Unsigned32
    MAX-ACCESS  read-only
    STATUS      current
    DESCRIPTION "The highest latency over the period."
    ::= { sproutLIRLatencyEntry 4 }

sproutLIRLatencyLWM OBJECT-TYPE
    SYNTAX      Unsigned32
    MAX-ACCESS  read-only
    STATUS      current
    DESCRIPTION "The lowest latency over the period."
    ::= { sproutLIRLatencyEntry 5 }

sproutLIRLatencyCount OBJECT-TYPE
    SYNTAX      Unsigned32
    MAX-ACCESS  read-only
    STATUS      current
    DESCRIPTION "The total requests over the period."
    ::= { sproutLIRLatencyEntry 6 }

sproutIncomingRequestsTable OBJECT-TYPE
    SYNTAX SEQUENCE OF SproutIncomingRequestsEntry
    MAX-ACCESS not-accessible
    STATUS current
    DESCRIPTION "Total number of incoming requests handled by this Sprout over
                 the given period."
    ::= { sprout 6 }

sproutIncomingRequestsEntry OBJECT-TYPE
    SYNTAX      SproutIncomingRequestsEntry
    MAX-ACCESS  not-accessible
    STATUS      current
    DESCRIPTION "The total number of incoming requests"
    INDEX       { sproutIncomingRequestsTimeFrame,
                  sproutIncomingRequestsScope }
    ::= { sproutIncomingRequestsTable 1 }

SproutIncomingRequestsEntry ::= SEQUENCE
{
  sproutIncomingRequestsTimeFrame      INTEGER,
  sproutIncomingRequestsScope          OCTET STRING,
  sproutIncomingRequestsCount          Unsigned32
}

sproutIncomingRequestsTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutIncomingRequestsEntry 1 }

sproutIncomingRequestsScope OBJECT-TYPE
    SYNTAX      OCTET STRING (SIZE(1..64))
    MAX-ACCESS  not-accessible
    STATUS      current
    DESCRIPTION "Statistic scope - should always take the value: node."
    ::= { sproutIncomingRequestsEntry 2 }

sproutIncomingRequestsCount OBJECT-TYPE
    SYNTAX      Unsigned32
    MAX-ACCESS  read-only
    STATUS      current
    DESCRIPTION "The total number of incoming requests over the period."
    ::= { sproutIncomingRequestsEntry 3 }

sproutRejectedOverloadTable OBJECT-TYPE
    SYNTAX SEQUENCE OF SproutRejectedOverloadEntry
    MAX-ACCESS not-accessible
    STATUS current
    DESCRIPTION "Total number of requests rejected due to overload by
                 this Sprout over the given period."
    ::= { sprout 7 }

sproutRejectedOverloadEntry OBJECT-TYPE
    SYNTAX      SproutRejectedOverloadEntry
    MAX-ACCESS  not-accessible
    STATUS      current
    DESCRIPTION "The total number of requests rejected due to overload"
    INDEX       { sproutRejectedOverloadTimeFrame,
                  sproutRejectedOverloadScope }
    ::= { sproutRejectedOverloadTable 1 }

SproutRejectedOverloadEntry ::= SEQUENCE
{
  sproutRejectedOverloadTimeFrame      INTEGER,
  sproutRejectedOverloadScope          OCTET STRING,
  sproutRejectedOverloadCount          Unsigned32
}

sproutRejectedOverloadTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutRejectedOverloadEntry 1 }

sproutRejectedOverloadScope OBJECT-TYPE
    SYNTAX      OCTET STRING (SIZE(1..64))
    MAX-ACCESS  not-accessible
    STATUS      current
    DESCRIPTION "Statistic scope - should always take the value: node."
    ::= { sproutRejectedOverloadEntry 2 }

sproutRejectedOverloadCount OBJECT-TYPE
    SYNTAX      Unsigned32
    MAX-ACCESS  read-only
    STATUS      current
    DESCRIPTION "The total number of rejected requests due to overload over the
                 period."
    ::= { sproutRejectedOverloadEntry 3 }

sproutQueueSizeTable OBJECT-TYPE
    SYNTAX SEQUENCE OF SproutQueueSizeEntry
    MAX-ACCESS not-accessible
    STATUS current
    DESCRIPTION "Average request queue size for this Sprout"
    ::= { sprout 8 }

sproutQueueSizeEntry OBJECT-TYPE
    SYNTAX      SproutQueueSizeEntry
    MAX-ACCESS  not-accessible
    STATUS      current
    DESCRIPTION "The average, variance, LWM and HWM of request queue size"
    INDEX       { sproutQueueSizeTimeFrame,
                  sproutQueueSizeScope }
    ::= { sproutQueueSizeTable 1 }

SproutQueueSizeEntry ::= SEQUENCE
{
  sproutQueueSizeTimeFrame      INTEGER,
  sproutQueueSizeScope          OCTET STRING,
  sproutQueueSizeAverage        Unsigned32,
  sproutQueueSizeVariance       Unsigned32,
  sproutQueueSizeHWM            Unsigned32,
  sproutQueueSizeLWM            Unsigned32,
  sproutQueueSizeCount          Unsigned32
}

sproutQueueSizeTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutQueueSizeEntry 1 }

sproutQueueSizeScope OBJECT-TYPE
    SYNTAX      OCTET STRING (SIZE(1..64))
    MAX-ACCESS  not-accessible
    STATUS      current
    DESCRIPTION "Statistic scope - should always take the value: node."
    ::= { sproutQueueSizeEntry 2 }

sproutQueueSizeAverage OBJECT-TYPE
    SYNTAX      Unsigned32
    MAX-ACCESS  read-only
    STATUS      current
    DESCRIPTION "The average request queue size over the period."
    ::= { sproutQueueSizeEntry 3 }

sproutQueueSizeVariance OBJECT-TYPE
    SYNTAX      Unsigned32
    MAX-ACCESS  read-only
    STATUS      current
    DESCRIPTION "The variance of the queue size over the period."
    ::= { sproutQueueSizeEntry 4 }

sproutQueueSizeHWM OBJECT-TYPE
    SYNTAX      Unsigned32
    MAX-ACCESS  read-only
    STATUS      current
    DESCRIPTION "The highest queue size over the period."
    ::= { sproutQueueSizeEntry 5 }

sproutQueueSizeLWM OBJECT-TYPE
    SYNTAX      Unsigned32
    MAX-ACCESS  read-only
    STATUS      current
    DESCRIPTION "The lowest queue size over the period."
    ::= { sproutQueueSizeEntry 6 }

sproutQueueSizeCount OBJECT-TYPE
    SYNTAX      Unsigned32
    MAX-ACCESS  read-only
    STATUS      current
    DESCRIPTION "The total requests over the period."
    ::= { sproutQueueSizeEntry 7 }

sproutSCSCFInitialRegistrationTable OBJECT-TYPE
    SYNTAX SEQUENCE OF SproutSCSCFInitialRegistrationEntry
    MAX-ACCESS not-accessible
    STATUS current
    DESCRIPTION "Counts the number of attempts, successes and failures
                 of initial registrations, and also (for convenience) provides
                 the percentage of initial registration attempts that were
                 successful.  Note that registrations that fail authentication
                 are not tracked in this table."
    ::= { sprout 9 }

sproutSCSCFInitialRegistrationEntry OBJECT-TYPE
    SYNTAX      SproutSCSCFInitialRegistrationEntry
    MAX-ACCESS  not-accessible
    STATUS      current
    DESCRIPTION "The number of attempts, successes and failures for
                 initial registrations, and the percentage of initial
                 registration attempts that were successful."
    INDEX       { sproutSCSCFInitialRegistrationScope }
    ::= { sproutSCSCFInitialRegistrationTable 1 }

SproutSCSCFInitialRegistrationEntry ::= SEQUENCE
{
  sproutSCSCFInitialRegistrationScope          INTEGER,
  sproutSCSCFInitialRegistrationAttempts       Unsigned32,
  sproutSCSCFInitialRegistrationSuccesses      Unsigned32,
  sproutSCSCFInitialRegistrationFailures       Unsigned32,
  sproutSCSCFInitialRegistrationSuccessPercent Unsigned32
}

sproutSCSCFInitialRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFInitialRegistrationEntry 1 }

sproutSCSCFInitialRegistrationAttempts OBJECT-TYPE
    SYNTAX      Unsigned32
    MAX-ACCESS  read-only
    STATUS      current
    DESCRIPTION "The number of initial registration attempts over the period."
    ::= { sproutSCSCFInitialRegistrationEntry 2 }

sproutSCSCFInitialRegistrationSuccesses OBJECT-TYPE
    SYNTAX      Unsigned32
    MAX-ACCESS  read-only
    STATUS      current
    DESCRIPTION "The number of initial registration successes over the period."
    ::= { sproutSCSCFInitialRegistrationEntry 3 }

sproutSCSCFInitialRegistrationFailures OBJECT-TYPE
    SYNTAX      Unsigned32
    MAX-ACCESS  read-only
    STATUS      current
    DESCRIPTION "The number of initial registration failures over the period.
                 Note that 3xx responses are counted as failures."
    ::= { sproutSCSCFInitialRegistrationEntry 4 }

sproutSCSCFInitialRegistrationSuccessPercent OBJECT-TYPE
    SYNTAX      Unsigned32
    UNITS       "/ 10000 %"
    MAX-ACCESS  read-only
    STATUS      current
    DESCRIPTION "The percentage of initial registrations over the
                 period that were successful. Reported in units of ten
                 thousandths of a percentage point. When there are zero
                 attempts made, the value will be 1000000 to represent 100%."
    ::= { sproutSCSCFInitialRegistrationEntry 5 }

sproutSCSCFReRegistrationTable OBJECT-TYPE
    SYNTAX SEQUENCE OF SproutSCSCFReRegistrationEntry
    MAX-ACCESS not-accessible
    STATUS current
    DESCRIPTION "Counts the number of attempts, successes and failures
                 of re-registrations, and also (for convenience) provides the
                 percentage of re-registration attempts that were successful.
                 Note that re-registrations that fail authentication are not
                 tracked in this table."
    ::= { sprout 10 }

sproutSCSCFReRegistrationEntry OBJECT-TYPE
    SYNTAX      SproutSCSCFReRegistrationEntry
    MAX-ACCESS  not-accessible
    STATUS      current
    DESCRIPTION "The number of attempts, successes and failures for
                 re-registrations, and the percentage of re-registration
                 attempts that were successful."
    INDEX       { sproutSCSCFReRegistrationScope }
    ::= { sproutSCSCFReRegistrationTable 1 }

SproutSCSCFReRegistrationEntry ::= SEQUENCE
{
  sproutSCSCFReRegistrationScope          INTEGER,
  sproutSCSCFReRegistrationAttempts       Unsigned32,
  sproutSCSCFReRegistrationSuccesses      Unsigned32,
  sproutSCSCFReRegistrationFailures       Unsigned32,
  sproutSCSCFReRegistrationSuccessPercent Unsigned32
}

sproutSCSCFReRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFReRegistrationEntry 1 }

sproutSCSCFReRegistrationAttempts OBJECT-TYPE
    SYNTAX      Unsigned32
    MAX-ACCESS  read-only
    STATUS      current
    DESCRIPTION "The number of re-registration attempts over the period."
    ::= { sproutSCSCFReRegistrationEntry 2 }

sproutSCSCFReRegistrationSuccesses OBJECT-TYPE
    SYNTAX      Unsigned32
    MAX-ACCESS  read-only
    STATUS      current
    DESCRIPTION "The number of re-registration successes over the period."
    ::= { sproutSCSCFReRegistrationEntry 3 }

sproutSCSCFReRegistrationFailures OBJECT-TYPE
    SYNTAX      Unsigned32
    MAX-ACCESS  read-only
    STATUS      current
    DESCRIPTION "The number of re-registration failures over the period. Note
                 that 3xx responses are counted as failures."
    ::= { sproutSCSCFReRegistrationEntry 4 }

sproutSCSCFReRegistrationSuccessPercent OBJECT-TYPE
    SYNTAX      Unsigned32
    UNITS       "/ 10000 %"
    MAX-ACCESS  read-only
    STATUS      current
    DESCRIPTION "The percentage of re-registrations attempts over the
                 period that were successful. Reported in units of ten
                 thousandths of a percentage point. When there are zero
                 attempts made, the value will be 1000000 to represent 100%."
    ::= { sproutSCSCFReRegistrationEntry 5 }

sproutSCSCFDeRegistrationTable OBJECT-TYPE
    SYNTAX SEQUENCE OF SproutSCSCFDeRegistrationEntry
    MAX-ACCESS not-accessible
    STATUS current
    DESCRIPTION "Counts the number of attempts, successes and failures
                 of de-registrations, and also (for convenience) provides the
                 percentage of de-registration attempts that were succesful."
    ::= { sprout 11 }

sproutSCSCFDeRegistrationEntry OBJECT-TYPE
    SYNTAX      SproutSCSCFDeRegistrationEntry
    MAX-ACCESS  not-accessible
    STATUS      current
    DESCRIPTION "The number of attempts, successes and failures for
                 de-registrations, and the percentage of de-registration
                 attempts that were successful."
    INDEX       { sproutSCSCFDeRegistrationScope }
    ::= { sproutSCSCFDeRegistrationTable 1 }

SproutSCSCFDeRegistrationEntry ::= SEQUENCE
{
  sproutSCSCFDeRegistrationScope          INTEGER,
  sproutSCSCFDeRegistrationAttempts       Unsigned32,
  sproutSCSCFDeRegistrationSuccesses      Unsigned32,
  sproutSCSCFDeRegistrationFailures       Unsigned32,
  sproutSCSCFDeRegistrationSuccessPercent Unsigned32
}

sproutSCSCFDeRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFDeRegistrationEntry 1 }

sproutSCSCFDeRegistrationAttempts OBJECT-TYPE
    SYNTAX      Unsigned32
    MAX-ACCESS  read-only
    STATUS      current
    DESCRIPTION "The number of de-registration attempts over the period."
    ::= { sproutSCSCFDeRegistrationEntry 2 }

sproutSCSCFDeRegistrationSuccesses OBJECT-TYPE
    SYNTAX      Unsigned32
    MAX-ACCESS  read-only
    STATUS      current
    DESCRIPTION "The number of de-registration successes over the period."
    ::= { sproutSCSCFDeRegistrationEntry 3 }

sproutSCSCFDeRegistrationFailures OBJECT-TYPE
    SYNTAX      Unsigned32
    MAX-ACCESS  read-only
    STATUS      current
    DESCRIPTION "The number of de-registration failures over the period. Note
                 that 3xx responses are counted as failures."
    ::= { sproutSCSCFDeRegistrationEntry 4 }

sproutSCSCFDeRegistrationSuccessPercent OBJECT-TYPE
    SYNTAX      Unsigned32
    UNITS       "/ 10000 %"
    MAX-ACCESS  read-only
    STATUS      current
    DESCRIPTION "The percentage of de-registration attempts over the time period
                 that were successful."
    ::= { sproutSCSCFDeRegistrationEntry 5 }

sproutSCSCFThirdPartyInitialRegistrationTable OBJECT-TYPE
    SYNTAX SEQUENCE OF SproutSCSCFThirdPartyInitialRegistrationEntry
    MAX-ACCESS not-accessible
    STATUS current
    DESCRIPTION "Counts the number of attempts, successes and failures
                 of third-party initial registrations, and also for convenience
                 provides the percentage of attempts that were successful."
    ::= { sprout 12 }

sproutSCSCFThirdPartyInitialRegistrationEntry OBJECT-TYPE
    SYNTAX      SproutSCSCFThirdPartyInitialRegistrationEntry
    MAX-ACCESS  not-accessible
    STATUS      current
    DESCRIPTION "The number of attempts, successes and failures for
                 third-party initial registrations, and the percentage of
                 attempts that were succesful."
    INDEX       { sproutSCSCFThirdPartyInitialRegistrationScope }
    ::= { sproutSCSCFThirdPartyInitialRegistrationTable 1 }

SproutSCSCFThirdPartyInitialRegistrationEntry ::= SEQUENCE
{
  sproutSCSCFThirdPartyInitialRegistrationScope          INTEGER,
  sproutSCSCFThirdPartyInitialRegistrationAttempts       Unsigned32,
  sproutSCSCFThirdPartyInitialRegistrationSuccesses      Unsigned32,
  sproutSCSCFThirdPartyInitialRegistrationFailures       Unsigned32,
  sproutSCSCFThirdPartyInitialRegistrationSuccessPercent Unsigned32
}

sproutSCSCFThirdPartyInitialRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFThirdPartyInitialRegistrationEntry 1 }

sproutSCSCFThirdPartyInitialRegistrationAttempts OBJECT-TYPE
    SYNTAX      Unsigned32
    MAX-ACCESS  read-only
    STATUS      current
    DESCRIPTION "The number of third-party initial registration attempts over
the period."
    ::= { sproutSCSCFThirdPartyInitialRegistrationEntry 2 }

sproutSCSCFThirdPartyInitialRegistrationSuccesses OBJECT-TYPE
    SYNTAX      Unsigned32
    MAX-ACCESS  read-only
    STATUS      current
    DESCRIPTION "The number of third-party initial registration successes over
                 the period."
    ::= { sproutSCSCFThirdPartyInitialRegistrationEntry 3 }

sproutSCSCFThirdPartyInitialRegistrationFailures OBJECT-TYPE
    SYNTAX      Unsigned32
    MAX-ACCESS  read-only
    STATUS      current
    DESCRIPTION "The number of third-party initial registration failures over
                 the period. Note that 3xx responses are counted as failures."
    ::= { sproutSCSCFThirdPartyInitialRegistrationEntry 4 }

sproutSCSCFThirdPartyInitialRegistrationSuccessPercent OBJECT-TYPE
    SYNTAX      Unsigned32
    UNITS       "/ 10000 %"
    MAX-ACCESS  read-only
    STATUS      current
    DESCRIPTION "The percentage of third-party initial registration attempts
                 over the time period that were successful. Reported in units
                 of ten thousandths of a percentage point. When there are zero
                 attempts made, the value will be 1000000 to represent 100%."
    ::= { sproutSCSCFThirdPartyInitialRegistrationEntry 5 }

sproutSCSCFThirdPartyReRegistrationTable OBJECT-TYPE
    SYNTAX SEQUENCE OF SproutSCSCFThirdPartyReRegistrationEntry
    MAX-ACCESS not-accessible
    STATUS current
    DESCRIPTION "Counts the number of attempts, successes and failures
                 of third-party re-registrations, and also (for convenience)
                 provides the percentage of attempts that were successful."
    ::= { sprout 13 }

sproutSCSCFThirdPartyReRegistrationEntry OBJECT-TYPE
    SYNTAX      SproutSCSCFThirdPartyReRegistrationEntry
    MAX-ACCESS  not-accessible
    STATUS      current
    DESCRIPTION "The number of attempts, successes and failures for
                 third-party re-registrations, and the percentage of attempts
                 that were successful."
    INDEX       { sproutSCSCFThirdPartyReRegistrationScope }
    ::= { sproutSCSCFThirdPartyReRegistrationTable 1 }

SproutSCSCFThirdPartyReRegistrationEntry ::= SEQUENCE
{
  sproutSCSCFThirdPartyReRegistrationScope          INTEGER,
  sproutSCSCFThirdPartyReRegistrationAttempts       Unsigned32,
  sproutSCSCFThirdPartyReRegistrationSuccesses      Unsigned32,
  sproutSCSCFThirdPartyReRegistrationFailures       Unsigned32,
  sproutSCSCFThirdPartyReRegistrationSuccessPercent Unsigned32
}

sproutSCSCFThirdPartyReRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFThirdPartyReRegistrationEntry 1 }

sproutSCSCFThirdPartyReRegistrationAttempts OBJECT-TYPE
    SYNTAX      Unsigned32
    MAX-ACCESS  read-only
    STATUS      current
    DESCRIPTION "The number of third-party re-registration attempts over the
                 period."
    ::= { sproutSCSCFThirdPartyReRegistrationEntry 2 }

sproutSCSCFThirdPartyReRegistrationSuccesses OBJECT-TYPE
    SYNTAX      Unsigned32
    MAX-ACCESS  read-only
    STATUS      current
    DESCRIPTION "The number of third-party re-registration successes over the
                 period."
    ::= { sproutSCSCFThirdPartyReRegistrationEntry 3 }

sproutSCSCFThirdPartyReRegistrationFailures OBJECT-TYPE
    SYNTAX      Unsigned32
    MAX-ACCESS  read-only
    STATUS      current
    DESCRIPTION "The number of third-party re-registration failures over the
                 period. Note that 3xx responses are counted as failures."
    ::= { sproutSCSCFThirdPartyReRegistrationEntry 4 }

sproutSCSCFThirdPartyReRegistrationSuccessPercent OBJECT-TYPE
    SYNTAX      Unsigned32
    UNITS       "/ 10000 %"
    MAX-ACCESS  read-only
    STATUS      current
    DESCRIPTION "The percentage of third-party re-registration attempts
                 over the time period that were successful. Reported in units
                 of ten thousandths of a percentage point. When there are zero
                 attempts made, the value will be 1000000 to represent 100%."
    ::= { sproutSCSCFThirdPartyReRegistrationEntry 5 }

sproutSCSCFThirdPartyDeRegistrationTable OBJECT-TYPE
    SYNTAX SEQUENCE OF SproutSCSCFThirdPartyDeRegistrationEntry
    MAX-ACCESS not-accessible
    STATUS current
    DESCRIPTION "Counts the number of attempts, successes and failures
                 of third-party de-registrations and also (for convenience)
                 provides the percentage of attempts that were successful."
    ::= { sprout 14 }

sproutSCSCFThirdPartyDeRegistrationEntry OBJECT-TYPE
    SYNTAX      SproutSCSCFThirdPartyDeRegistrationEntry
    MAX-ACCESS  not-accessible
    STATUS      current
    DESCRIPTION "The number of attempts, successes and failures for
                 third-party de-registrations, and the percentage of attempts
                 that were successful."
    INDEX       { sproutSCSCFThirdPartyDeRegistrationScope }
    ::= { sproutSCSCFThirdPartyDeRegistrationTable 1 }

SproutSCSCFThirdPartyDeRegistrationEntry ::= SEQUENCE
{
  sproutSCSCFThirdPartyDeRegistrationScope          INTEGER,
  sproutSCSCFThirdPartyDeRegistrationAttempts       Unsigned32,
  sproutSCSCFThirdPartyDeRegistrationSuccesses      Unsigned32,
  sproutSCSCFThirdPartyDeRegistrationFailures       Unsigned32,
  sproutSCSCFThirdPartyDeRegistrationSuccessPercent Unsigned32
}

sproutSCSCFThirdPartyDeRegistrationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFThirdPartyDeRegistrationEntry 1 }

sproutSCSCFThirdPartyDeRegistrationAttempts OBJECT-TYPE
    SYNTAX      Unsigned32
    MAX-ACCESS  read-only
    STATUS      current
    DESCRIPTION "The number of third-party de-registration attempts over the
                 period."
    ::= { sproutSCSCFThirdPartyDeRegistrationEntry 2 }

sproutSCSCFThirdPartyDeRegistrationSuccesses OBJECT-TYPE
    SYNTAX      Unsigned32
    MAX-ACCESS  read-only
    STATUS      current
    DESCRIPTION "The number of third-party de-registration successes over the
                 period."
    ::= { sproutSCSCFThirdPartyDeRegistrationEntry 3 }

sproutSCSCFThirdPartyDeRegistrationFailures OBJECT-TYPE
    SYNTAX      Unsigned32
    MAX-ACCESS  read-only
    STATUS      current
    DESCRIPTION "The number of third-party de-registration failures over the
                 period. Note that 3xx responses are counted as failures."
    ::= { sproutSCSCFThirdPartyDeRegistrationEntry 4 }

sproutSCSCFThirdPartyDeRegistrationSuccessPercent OBJECT-TYPE
    SYNTAX      Unsigned32
    UNITS       "/ 10000 %"
    MAX-ACCESS  read-only
    STATUS      current
    DESCRIPTION "The percentage of third-party de-registration attempts
                 over the time period that were successful. Reported in units
                 of ten thousandths of a percentage point. When there are zero
                 attempts made, the value will be 1000000 to represent 100%."
    ::= { sproutSCSCFThirdPartyDeRegistrationEntry 5 }

sproutSCSCFSIPDigestAuthenticationTable OBJECT-TYPE
    SYNTAX SEQUENCE OF SproutSCSCFSIPDigestAuthenticationEntry
    MAX-ACCESS not-accessible
    STATUS current
    DESCRIPTION "Counts the number of attempts, successes and failures
                 of SIP digest authentications on register requests, and (for
                 convenience) the percentage of attempts that were successful."
    ::= { sprout 15 }

sproutSCSCFSIPDigestAuthenticationEntry OBJECT-TYPE
    SYNTAX      SproutSCSCFSIPDigestAuthenticationEntry
    MAX-ACCESS  not-accessible
    STATUS      current
    DESCRIPTION "The number of attempts, successes and failures for
                 SIP digest authentications on register requests, and the
                 percentage of attempts that were successful."
    INDEX       { sproutSCSCFSIPDigestAuthenticationScope }
    ::= { sproutSCSCFSIPDigestAuthenticationTable 1 }

SproutSCSCFSIPDigestAuthenticationEntry ::= SEQUENCE
{
  sproutSCSCFSIPDigestAuthenticationScope          INTEGER,
  sproutSCSCFSIPDigestAuthenticationAttempts       Unsigned32,
  sproutSCSCFSIPDigestAuthenticationSuccesses      Unsigned32,
  sproutSCSCFSIPDigestAuthenticationFailures       Unsigned32,
  sproutSCSCFSIPDigestAuthenticationSuccessPercent Unsigned32
}

sproutSCSCFSIPDigestAuthenticationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFSIPDigestAuthenticationEntry 1 }

sproutSCSCFSIPDigestAuthenticationAttempts OBJECT-TYPE
    SYNTAX      Unsigned32
    MAX-ACCESS  read-only
    STATUS      current
    DESCRIPTION "The number of SIP digest authentication attempts on register
                 requests over the period."
    ::= { sproutSCSCFSIPDigestAuthenticationEntry 2 }

sproutSCSCFSIPDigestAuthenticationSuccesses OBJECT-TYPE
    SYNTAX      Unsigned32
    MAX-ACCESS  read-only
    STATUS      current
    DESCRIPTION "The number of SIP digest authentication successes on register
                 requests over the period."
    ::= { sproutSCSCFSIPDigestAuthenticationEntry 3 }

sproutSCSCFSIPDigestAuthenticationFailures OBJECT-TYPE
    SYNTAX      Unsigned32
    MAX-ACCESS  read-only
    STATUS      current
    DESCRIPTION "The number of SIP digest authentication failures on register
                 requests over the period."
    ::= { sproutSCSCFSIPDigestAuthenticationEntry 4 }

sproutSCSCFSIPDigestAuthenticationSuccessPercent OBJECT-TYPE
    SYNTAX      Unsigned32
    UNITS       "/ 10000 %"
    MAX-ACCESS  read-only
    STATUS      current
    DESCRIPTION "The percentage of SIP digest authentication attempts over
                 the time period that were successful. Reported in units of ten
                 thousandths of a percentage point. When there are zero
                 attempts made, the value will be 1000000 to represent 100%."
    ::= { sproutSCSCFSIPDigestAuthenticationEntry 5 }

sproutSCSCFAKAAuthenticationTable OBJECT-TYPE
    SYNTAX SEQUENCE OF SproutSCSCFAKAAuthenticationEntry
    MAX-ACCESS not-accessible
    STATUS current
    DESCRIPTION "Counts the number of attempts, successes and failures
                 of AKA authentications on register requests, and (for
                 convenience) provides the percentage of attempts that were
                 successful."
    ::= { sprout 16 }

sproutSCSCFAKAAuthenticationEntry OBJECT-TYPE
    SYNTAX      SproutSCSCFAKAAuthenticationEntry
    MAX-ACCESS  not-accessible
    STATUS      current
    DESCRIPTION "The number of attempts, successes and failures for
                 AKA authentications on register requests, and the percentage
                 of attempts that were successful."
    INDEX       { sproutSCSCFAKAAuthenticationScope }
    ::= { sproutSCSCFAKAAuthenticationTable 1 }

SproutSCSCFAKAAuthenticationEntry ::= SEQUENCE
{
  sproutSCSCFAKAAuthenticationScope          INTEGER,
  sproutSCSCFAKAAuthenticationAttempts       Unsigned32,
  sproutSCSCFAKAAuthenticationSuccesses      Unsigned32,
  sproutSCSCFAKAAuthenticationFailures       Unsigned32,
  sproutSCSCFAKAAuthenticationSuccessPercent Unsigned32
}

sproutSCSCFAKAAuthenticationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFAKAAuthenticationEntry 1 }

sproutSCSCFAKAAuthenticationAttempts OBJECT-TYPE
    SYNTAX      Unsigned32
    MAX-ACCESS  read-only
    STATUS      current
    DESCRIPTION "The number of AKA authentication attempts on register
                 requests over the period."
    ::= { sproutSCSCFAKAAuthenticationEntry 2 }

sproutSCSCFAKAAuthenticationSuccesses OBJECT-TYPE
    SYNTAX      Unsigned32
    MAX-ACCESS  read-only
    STATUS      current
    DESCRIPTION "The number of AKA authentication successes on register
                 requests over the period."
    ::= { sproutSCSCFAKAAuthenticationEntry 3 }

sproutSCSCFAKAAuthenticationFailures OBJECT-TYPE
    SYNTAX      Unsigned32
    MAX-ACCESS  read-only
    STATUS      current
    DESCRIPTION "The number of AKA authentication failures on register
                 requests over the period."
    ::= { sproutSCSCFAKAAuthenticationEntry 4 }

sproutSCSCFAKAAuthenticationSuccessPercent OBJECT-TYPE
    SYNTAX      Unsigned32
    UNITS       "/ 10000 %"
    MAX-ACCESS  read-only
    STATUS      current
    DESCRIPTION "The percentage of AKA authentication attempts over
                 the time period that were successful. Reported in units of ten
                 thousandths of a percentage point. When there are zero
                 attempts made, the value will be 1000000 to represent 100%."
    ::= { sproutSCSCFAKAAuthenticationEntry 5 }

sproutSCSCFNonRegisterAuthenticationTable OBJECT-TYPE
    SYNTAX SEQUENCE OF SproutSCSCFNonRegisterAuthenticationEntry
    MAX-ACCESS not-accessible
    STATUS current
    DESCRIPTION "Counts the number of attempts, successes and failures
                 of non-register authentication requests, and (for
                 convenience) provides the percentage of attempts that were
                 successful."
    ::= { sprout 17 }

sproutSCSCFNonRegisterAuthenticationEntry OBJECT-TYPE
    SYNTAX      SproutSCSCFNonRegisterAuthenticationEntry
    MAX-ACCESS  not-accessible
    STATUS      current
    DESCRIPTION "The number of attempts, successes and failures for
                 non-register authentication requests"
    INDEX       { sproutSCSCFNonRegisterAuthenticationScope }
    ::= { sproutSCSCFNonRegisterAuthenticationTable 1 }

SproutSCSCFNonRegisterAuthenticationEntry ::= SEQUENCE
{
  sproutSCSCFNonRegisterAuthenticationScope          INTEGER,
  sproutSCSCFNonRegisterAuthenticationAttempts       Unsigned32,
  sproutSCSCFNonRegisterAuthenticationSuccesses      Unsigned32,
  sproutSCSCFNonRegisterAuthenticationFailures       Unsigned32,
  sproutSCSCFNonRegisterAuthenticationSuccessPercent Unsigned32
}

sproutSCSCFNonRegisterAuthenticationScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFNonRegisterAuthenticationEntry 1 }

sproutSCSCFNonRegisterAuthenticationAttempts OBJECT-TYPE
    SYNTAX      Unsigned32
    MAX-ACCESS  read-only
    STATUS      current
    DESCRIPTION "The number of non-register authentication attempts on register
                 requests over the period."
    ::= { sproutSCSCFNonRegisterAuthenticationEntry 2 }

sproutSCSCFNonRegisterAuthenticationSuccesses OBJECT-TYPE
    SYNTAX      Unsigned32
    MAX-ACCESS  read-only
    STATUS      current
    DESCRIPTION "The number of non-register authentication successes on register
                 requests over the period."
    ::= { sproutSCSCFNonRegisterAuthenticationEntry 3 }

sproutSCSCFNonRegisterAuthenticationFailures OBJECT-TYPE
    SYNTAX      Unsigned32
    MAX-ACCESS  read-only
    STATUS      current
    DESCRIPTION "The number of non-register authentication failures on register
                 requests over the period."
    ::= { sproutSCSCFNonRegisterAuthenticationEntry 4 }

sproutSCSCFNonRegisterAuthenticationSuccessPercent OBJECT-TYPE
    SYNTAX      Unsigned32
    UNITS       "/ 10000 %"
    MAX-ACCESS  read-only
    STATUS      current
    DESCRIPTION "The percentage of non-register authentication attempts over the
                 period that were successful. Reported in units of ten
                 thousandths of a percentage point. When there are zero
                 attempts made, the value will be 1000000 to represent 100%."
    ::= { sproutSCSCFNonRegisterAuthenticationEntry 5 }

sproutICSCFIncomingSIPTransactionsTable OBJECT-TYPE
    SYNTAX SEQUENCE OF SproutICSCFIncomingSIPTransactionsEntry
    MAX-ACCESS not-accessible
    STATUS current
    DESCRIPTION "Counts the number of attempts, successes and failures
                 of incoming SIP transactions for the ICSCF, and (for
                 convenience) provides the percentage of attempts that were
                 successful. Note that CANCEL transactions are not currently
                 tracked in this table."
    ::= { sprout 18 }

sproutICSCFIncomingSIPTransactionsEntry OBJECT-TYPE
    SYNTAX      SproutICSCFIncomingSIPTransactionsEntry
    MAX-ACCESS  not-accessible
    STATUS      current
    DESCRIPTION "The number of attempts, successes and failures for
                 incoming SIP transactions for the ICSCF, and the percentage
                 of attempts that were successful."
    INDEX       { sproutICSCFIncomingSIPTransactionsTimeScope,
                  sproutICSCFIncomingSIPTransactionsRequestScope }
    ::= { sproutICSCFIncomingSIPTransactionsTable 1 }

SproutICSCFIncomingSIPTransactionsEntry ::= SEQUENCE
{
  sproutICSCFIncomingSIPTransactionsTimeScope      INTEGER,
  sproutICSCFIncomingSIPTransactionsRequestScope   INTEGER,
  sproutICSCFIncomingSIPTransactionsAttempts       Unsigned32,
  sproutICSCFIncomingSIPTransactionsSuccesses      Unsigned32,
  sproutICSCFIncomingSIPTransactionsFailures       Unsigned32,
  sproutICSCFIncomingSIPTransactionsSuccessPercent Unsigned32
}

sproutICSCFIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutICSCFIncomingSIPTransactionsEntry 1 }

sproutICSCFIncomingSIPTransactionsRequestScope OBJECT-TYPE
    SYNTAX      RequestType
    MAX-ACCESS  not-accessible
    STATUS      current
    DESCRIPTION "The method type of the incoming transaction."
    ::= { sproutICSCFIncomingSIPTransactionsEntry 2 }

sproutICSCFIncomingSIPTransactionsAttempts OBJECT-TYPE
    SYNTAX      Unsigned32
    MAX-ACCESS  read-only
    STATUS      current
    DESCRIPTION "The number of incoming SIP transactions over the time period."
    ::= { sproutICSCFIncomingSIPTransactionsEntry 3 }

sproutICSCFIncomingSIPTransactionsSuccesses OBJECT-TYPE
    SYNTAX      Unsigned32
    MAX-ACCESS  read-only
    STATUS      current
    DESCRIPTION "The number of successful incoming SIP transactions over the
                 time period."
    ::= { sproutICSCFIncomingSIPTransactionsEntry 4 }

sproutICSCFIncomingSIPTransactionsFailures OBJECT-TYPE
    SYNTAX      Unsigned32
    MAX-ACCESS  read-only
    STATUS      current
    DESCRIPTION "The number of failed incoming SIP transactions over the
                 time period. Note that 3xx responses are counted as
                 transaction failures."
    ::= { sproutICSCFIncomingSIPTransactionsEntry 5 }

sproutICSCFIncomingSIPTransactionsSuccessPercent OBJECT-TYPE
    SYNTAX      Unsigned32
    UNITS       "/ 10000 %"
    MAX-ACCESS  read-only
    STATUS      current
    DESCRIPTION "The percentage of incoming SIP transactions over the
                 period that were successful. Reported in units of ten
                 thousandths of a percentage point. When there are zero
                 attempts made, the value will be 1000000 to represent 100%."
    ::= { sproutICSCFIncomingSIPTransactionsEntry 6 }

sproutICSCFOutgoingSIPTransactionsTable OBJECT-TYPE
    SYNTAX SEQUENCE OF SproutICSCFOutgoingSIPTransactionsEntry
    MAX-ACCESS not-accessible
    STATUS current
    DESCRIPTION "Counts the number of attempts, successes and failures
                 of outgoing SIP transactions for the ICSCF, and (for
                 convenience) provides the percentage of attempts that were
                 successful.  Note that CANCEL transactions are not currently
                 tracked in this table."
    ::= { sprout 19 }

sproutICSCFOutgoingSIPTransactionsEntry OBJECT-TYPE
    SYNTAX      SproutICSCFOutgoingSIPTransactionsEntry
    MAX-ACCESS  not-accessible
    STATUS      current
    DESCRIPTION "The number of attempts, successes and failures for
                 outgoing SIP transactions for the ICSCF, and the percentage
                 of attempts that were successful."
    INDEX       { sproutICSCFOutgoingSIPTransactionsTimeScope,
                  sproutICSCFOutgoingSIPTransactionsRequestScope }
    ::= { sproutICSCFOutgoingSIPTransactionsTable 1 }

SproutICSCFOutgoingSIPTransactionsEntry ::= SEQUENCE
{
  sproutICSCFOutgoingSIPTransactionsTimeScope      INTEGER,
  sproutICSCFOutgoingSIPTransactionsRequestScope   INTEGER,
  sproutICSCFOutgoingSIPTransactionsAttempts       Unsigned32,
  sproutICSCFOutgoingSIPTransactionsSuccesses      Unsigned32,
  sproutICSCFOutgoingSIPTransactionsFailures       Unsigned32,
  sproutICSCFOutgoingSIPTransactionsSuccessPercent Unsigned32
}

sproutICSCFOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutICSCFOutgoingSIPTransactionsEntry 1 }

sproutICSCFOutgoingSIPTransactionsRequestScope OBJECT-TYPE
    SYNTAX      RequestType
    MAX-ACCESS  not-accessible
    STATUS      current
    DESCRIPTION "The method type of the outgoing transaction."
    ::= { sproutICSCFOutgoingSIPTransactionsEntry 2 }

sproutICSCFOutgoingSIPTransactionsAttempts OBJECT-TYPE
    SYNTAX      Unsigned32
    MAX-ACCESS  read-only
    STATUS      current
    DESCRIPTION "The number of outgoing SIP transactions over the time period."
    ::= { sproutICSCFOutgoingSIPTransactionsEntry 3 }

sproutICSCFOutgoingSIPTransactionsSuccesses OBJECT-TYPE
    SYNTAX      Unsigned32
    MAX-ACCESS  read-only
    STATUS      current
    DESCRIPTION "The number of successful outgoing SIP transactions over the
                 time period."
    ::= { sproutICSCFOutgoingSIPTransactionsEntry 4 }

sproutICSCFOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { sproutICSCFOutgoingSIPTransactionsEntry 5 }

sproutICSCFOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { sproutICSCFOutgoingSIPTransactionsEntry 6 }

sproutSCSCFIncomingSIPTransactionsTable OBJECT-TYPE
    SYNTAX SEQUENCE OF SproutSCSCFIncomingSIPTransactionsEntry
    MAX-ACCESS not-accessible
    STATUS current
    DESCRIPTION "Counts the number of attempts, successes and failures
                 of incoming SIP transactions for the SCSCF, and also (for
                 convenience) provides the percentage of incoming transaction
                 attempts that were successful.  Note that the following
                 transactions are not currently tracked in this table:
                 - CANCELs (see specific Cancel stats instead)
                 - REGISTERs (see specific Registration stats instead)
                 - Requests that fail authentication (see specific
                   Authentication stats instead)
                 - reg-event SUBSCRIBEs."
    ::= { sprout 20 }

sproutSCSCFIncomingSIPTransactionsEntry OBJECT-TYPE
    SYNTAX      SproutSCSCFIncomingSIPTransactionsEntry
    MAX-ACCESS  not-accessible
    STATUS      current
    DESCRIPTION "The number of attempts, successes and failures for
                 incoming SIP transactions for the SCSCF, and also the
                 percentage of incoming transaction attempts that were
                 successful."
    INDEX       { sproutSCSCFIncomingSIPTransactionsTimeScope,
                  sproutSCSCFIncomingSIPTransactionsRequestScope }
    ::= { sproutSCSCFIncomingSIPTransactionsTable 1 }

SproutSCSCFIncomingSIPTransactionsEntry ::= SEQUENCE
{
  sproutSCSCFIncomingSIPTransactionsTimeScope      INTEGER,
  sproutSCSCFIncomingSIPTransactionsRequestScope   INTEGER,
  sproutSCSCFIncomingSIPTransactionsAttempts       Unsigned32,
  sproutSCSCFIncomingSIPTransactionsSuccesses      Unsigned32,
  sproutSCSCFIncomingSIPTransactionsFailures       Unsigned32,
  sproutSCSCFIncomingSIPTransactionsSuccessPercent Unsigned32
}

sproutSCSCFIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFIncomingSIPTransactionsEntry 1 }

sproutSCSCFIncomingSIPTransactionsRequestScope OBJECT-TYPE
    SYNTAX      RequestType
    MAX-ACCESS  not-accessible
    STATUS      current
    DESCRIPTION "The method type of the incoming transaction."
    ::= { sproutSCSCFIncomingSIPTransactionsEntry 2 }

sproutSCSCFIncomingSIPTransactionsAttempts OBJECT-TYPE
    SYNTAX      Unsigned32
    MAX-ACCESS  read-only
    STATUS      current
    DESCRIPTION "The number of incoming SIP transactions over the time period."
    ::= { sproutSCSCFIncomingSIPTransactionsEntry 3 }

sproutSCSCFIncomingSIPTransactionsSuccesses OBJECT-TYPE
    SYNTAX      Unsigned32
    MAX-ACCESS  read-only
    STATUS      current
    DESCRIPTION "The number of successful incoming SIP transactions over the
                 time period."
    ::= { sproutSCSCFIncomingSIPTransactionsEntry 4 }

sproutSCSCFIncomingSIPTransactionsFailures OBJECT-TYPE
    SYNTAX      Unsigned32
    MAX-ACCESS  read-only
    STATUS      current
    DESCRIPTION "The number of failed incoming SIP transactions over the
                 time period. Note that 3xx responses are counted as
                 transaction failures."
    ::= { sproutSCSCFIncomingSIPTransactionsEntry 5 }

sproutSCSCFIncomingSIPTransactionsSuccessPercent OBJECT-TYPE
    SYNTAX      Unsigned32
    UNITS       "/ 10000 %"
    MAX-ACCESS  read-only
    STATUS      current
    DESCRIPTION "The percentage of incoming SIP transactions over the time
                 period that were successful. Reported in units of ten
                 thousandths of a percentage point. When there are zero
                 attempts made, the value will be 1000000 to represent 100%."
    ::= { sproutSCSCFIncomingSIPTransactionsEntry 6 }

sproutSCSCFOutgoingSIPTransactionsTable OBJECT-TYPE
    SYNTAX SEQUENCE OF SproutSCSCFOutgoingSIPTransactionsEntry
    MAX-ACCESS not-accessible
    STATUS current
    DESCRIPTION "Counts the number of attempts, successes and failures
                 of outgoing SIP transactions for the SCSCF, and (for
                 convenience) provides the percentage of attempts that were
                 successful.  Note that the following transactions are not
                 currently tracked in this table:
                 - CANCELs
                 - reg-event NOTIFYs."
    ::= { sprout 21 }

sproutSCSCFOutgoingSIPTransactionsEntry OBJECT-TYPE
    SYNTAX      SproutSCSCFOutgoingSIPTransactionsEntry
    MAX-ACCESS  not-accessible
    STATUS      current
    DESCRIPTION "The number of attempts, successes and failures for
                 outgoing SIP transactions for the SCSCF, and the percentage
                 of attempts that were successful."
    INDEX       { sproutSCSCFOutgoingSIPTransactionsTimeScope,
                  sproutSCSCFOutgoingSIPTransactionsRequestScope }
    ::= { sproutSCSCFOutgoingSIPTransactionsTable 1 }

SproutSCSCFOutgoingSIPTransactionsEntry ::= SEQUENCE
{
  sproutSCSCFOutgoingSIPTransactionsTimeScope      INTEGER,
  sproutSCSCFOutgoingSIPTransactionsRequestScope   INTEGER,
  sproutSCSCFOutgoingSIPTransactionsAttempts       Unsigned32,
  sproutSCSCFOutgoingSIPTransactionsSuccesses      Unsigned32,
  sproutSCSCFOutgoingSIPTransactionsFailures       Unsigned32,
  sproutSCSCFOutgoingSIPTransactionsSuccessPercent Unsigned32
}

sproutSCSCFOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFOutgoingSIPTransactionsEntry 1 }

sproutSCSCFOutgoingSIPTransactionsRequestScope OBJECT-TYPE
    SYNTAX      RequestType
    MAX-ACCESS  not-accessible
    STATUS      current
    DESCRIPTION "The method type of the outgoing transaction."
    ::= { sproutSCSCFOutgoingSIPTransactionsEntry 2 }

sproutSCSCFOutgoingSIPTransactionsAttempts OBJECT-TYPE
    SYNTAX      Unsigned32
    MAX-ACCESS  read-only
    STATUS      current
    DESCRIPTION "The number of outgoing SIP transactions over the time period."
    ::= { sproutSCSCFOutgoingSIPTransactionsEntry 3 }

sproutSCSCFOutgoingSIPTransactionsSuccesses OBJECT-TYPE
    SYNTAX      Unsigned32
    MAX-ACCESS  read-only
    STATUS      current
    DESCRIPTION "The number of successful outgoing SIP transactions over the
                 time period."
    ::= { sproutSCSCFOutgoingSIPTransactionsEntry 4 }

sproutSCSCFOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { sproutSCSCFOutgoingSIPTransactionsEntry 5 }

sproutSCSCFOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { sproutSCSCFOutgoingSIPTransactionsEntry 6 }

sproutSCSCFRequestsRoutedByPreloadedRouteTable OBJECT-TYPE
    SYNTAX SEQUENCE OF SproutRequestsRoutedByPreloadedRouteEntry
    MAX-ACCESS not-accessible
    STATUS current
    DESCRIPTION "Number of requests routed according to a pre-loaded route by
                 the SCSCF over the given time period."
    ::= { sprout 26 }

sproutSCSCFRequestsRoutedByPreloadedRouteEntry OBJECT-TYPE
    SYNTAX      SproutRequestsRoutedByPreloadedRouteEntry
    MAX-ACCESS  not-accessible
    STATUS      current
    DESCRIPTION "The number of requests routed according to a pre-loaded route
                 by the SCSCF."
    INDEX       { sproutSCSCFRequestsRoutedByPreloadedRouteScope }
    ::= { sproutSCSCFRequestsRoutedByPreloadedRouteTable 1 }

SproutRequestsRoutedByPreloadedRouteEntry ::= SEQUENCE
{
  sproutSCSCFRequestsRoutedByPreloadedRouteScope        INTEGER,
  sproutSCSCFRequestsRoutedByPreloadedRouteCount        Unsigned32
}

sproutSCSCFRequestsRoutedByPreloadedRouteScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFRequestsRoutedByPreloadedRouteEntry 1 }

sproutSCSCFRequestsRoutedByPreloadedRouteCount OBJECT-TYPE
    SYNTAX      Unsigned32
    MAX-ACCESS  read-only
    STATUS      current
    DESCRIPTION "The number of requests routed according to a pre-loaded route
                 over the given time period."
    ::= { sproutSCSCFRequestsRoutedByPreloadedRouteEntry 2 }


sproutPRRTable OBJECT-TYPE
    SYNTAX SEQUENCE OF SproutPRREntry
    MAX-ACCESS not-accessible
    STATUS     current
    DESCRIPTION "Statistics for the value of the permitted request rate.
                 The permitted request rate (PRR) is an estimate for the
                 sustainable request rate without causing large latency."
    ::= { sprout 27 }

sproutPRREntry OBJECT-TYPE
    SYNTAX      SproutPRREntry
    MAX-ACCESS  not-accessible
    STATUS      current
    DESCRIPTION "The average, variance, HWM, LWM and count of the permitted request rate"
    INDEX       { sproutPRRTimeFrame,
                  sproutPRRScope }
    ::= { sproutPRRTable 1 }

SproutPRREntry ::= SEQUENCE
{
  sproutPRRTimeFrame      INTEGER,
  sproutPRRScope          OCTET STRING,
  sproutPRRAverage        Unsigned32,
  sproutPRRVariance       Unsigned32,
  sproutPRRHWM            Unsigned32,
  sproutPRRLWM            Unsigned32,
  sproutPRRCount          Unsigned32
}

sproutPRRTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutPRREntry 1 }

sproutPRRScope OBJECT-TYPE
    SYNTAX      OCTET STRING (SIZE(1..64))
    MAX-ACCESS  not-accessible
    STATUS      current
    DESCRIPTION "Statistic scope - should always take the value: node."
    ::= { sproutPRREntry 2 }

sproutPRRAverage OBJECT-TYPE
    SYNTAX      Unsigned32
    MAX-ACCESS  read-only
    STATUS      current
    DESCRIPTION "The average permitted request rate over the period."
    ::= { sproutPRREntry 3 }

sproutPRRVariance OBJECT-TYPE
    SYNTAX      Unsigned32
    MAX-ACCESS  read-only
    STATUS      current
    DESCRIPTION "The variance of the permitted request rate over the period."
    ::= { sproutPRREntry 4 }

sproutPRRHWM OBJECT-TYPE
    SYNTAX      Unsigned32
    MAX-ACCESS  read-only
    STATUS      current
    DESCRIPTION "The highest permitted request rate over the period."
    ::= { sproutPRREntry 5 }

sproutPRRLWM OBJECT-TYPE
    SYNTAX      Unsigned32
    MAX-ACCESS  read-only
    STATUS      current
    DESCRIPTION "The lowest permitted request rate over the period."
    ::= { sproutPRREntry 6 }

sproutPRRCount OBJECT-TYPE
    SYNTAX      Unsigned32
    MAX-ACCESS  read-only
    STATUS      current
    DESCRIPTION "The total number of permitted request rate
                 updates over the period."
    ::= { sproutPRREntry 7 }

sproutSmoothedLatencyTable OBJECT-TYPE
    SYNTAX SEQUENCE OF SproutSmoothedLatencyEntry
    MAX-ACCESS not-accessible
    STATUS     current
    DESCRIPTION "The smoothed latency at last PRR update.
                 The permitted request rate (PRR) is an estimate for the
                 sustainable request rate without causing large latency."
    ::= { sprout 28 }

sproutSmoothedLatencyEntry OBJECT-TYPE
    SYNTAX      SproutSmoothedLatencyEntry
    MAX-ACCESS  not-accessible
    STATUS      current
    DESCRIPTION "The smoothed latency."
    INDEX       { sproutSmoothedLatencyScope }
    ::= { sproutSmoothedLatencyTable 1 }

SproutSmoothedLatencyEntry ::= SEQUENCE
{
  sproutSmoothedLatencyScope          OCTET STRING,
  sproutSmoothedLatencyValue          Unsigned32
}

sproutSmoothedLatencyScope OBJECT-TYPE
    SYNTAX      OCTET STRING (SIZE(1..64))
    MAX-ACCESS  not-accessible
    STATUS      current
    DESCRIPTION "Statistic scope - should always take the value: node."
    ::= { sproutSmoothedLatencyEntry 1 }

sproutSmoothedLatencyValue OBJECT-TYPE
    SYNTAX      Unsigned32
    MAX-ACCESS  read-only
    STATUS      current
    DESCRIPTION "The smoothed latency at last PRR update."
    ::= { sproutSmoothedLatencyEntry 2 }

sproutTargetLatencyTable OBJECT-TYPE
    SYNTAX SEQUENCE OF SproutTargetLatencyEntry
    MAX-ACCESS not-accessible
    STATUS     current
    DESCRIPTION "The maximum acceptable latency that
    should be experienced by requests."
    ::= { sprout 29 }

sproutTargetLatencyEntry OBJECT-TYPE
    SYNTAX      SproutTargetLatencyEntry
    MAX-ACCESS  not-accessible
    STATUS      current
    DESCRIPTION "The target latency."
    INDEX       { sproutTargetLatencyScope }
    ::= { sproutTargetLatencyTable 1 }

SproutTargetLatencyEntry ::= SEQUENCE
{
  sproutTargetLatencyScope          OCTET STRING,
  sproutTargetLatencyValue          Unsigned32
}

sproutTargetLatencyScope OBJECT-TYPE
    SYNTAX      OCTET STRING (SIZE(1..64))
    MAX-ACCESS  not-accessible
    STATUS      current
    DESCRIPTION "Statistic scope - should always take the value: node."
    ::= { sproutTargetLatencyEntry 1 }

sproutTargetLatencyValue OBJECT-TYPE
    SYNTAX      Unsigned32
    MAX-ACCESS  read-only
    STATUS      current
    DESCRIPTION "The target latency."
    ::= { sproutTargetLatencyEntry 2 }

sproutPenaltiesTable OBJECT-TYPE
    SYNTAX SEQUENCE OF SproutPenaltiesEntry
    MAX-ACCESS not-accessible
    STATUS     current
    DESCRIPTION "The number of overload responses
                 Sprout received from upstream at last PRR update.
                 The permitted request rate (PRR) is an estimate for the
                 sustainable request rate without causing large latency."
    ::= { sprout 30 }

sproutPenaltiesEntry OBJECT-TYPE
    SYNTAX      SproutPenaltiesEntry
    MAX-ACCESS  not-accessible
    STATUS      current
    DESCRIPTION "The penalty value."
    INDEX       { sproutPenaltiesScope }
    ::= { sproutPenaltiesTable 1 }

SproutPenaltiesEntry ::= SEQUENCE
{
  sproutPenaltiesScope        OCTET STRING,
  sproutPenaltiesValue        Unsigned32
}

sproutPenaltiesScope OBJECT-TYPE
    SYNTAX      OCTET STRING (SIZE(1..64))
    MAX-ACCESS  not-accessible
    STATUS      current
    DESCRIPTION "Statistic scope - should always take the value: node."
    ::= { sproutPenaltiesEntry 1 }

sproutPenaltiesValue OBJECT-TYPE
    SYNTAX      Unsigned32
    MAX-ACCESS  read-only
    STATUS      current
    DESCRIPTION "The number of overload responses."
    ::= { sproutPenaltiesEntry 2 }

sproutPRRCurrentTable OBJECT-TYPE
    SYNTAX SEQUENCE OF SproutPRRCurrentEntry
    MAX-ACCESS not-accessible
    STATUS     current
    DESCRIPTION "The curent permitted request rate.
                 The permitted request rate (PRR) is an estimate for the
                 sustainable request rate without causing large latency."
    ::= { sprout 31 }

sproutPRRCurrentEntry OBJECT-TYPE
    SYNTAX      SproutPRRCurrentEntry
    MAX-ACCESS  not-accessible
    STATUS      current
    DESCRIPTION "The smoothed latency."
    INDEX       { sproutPRRCurrentScope }
    ::= { sproutPRRCurrentTable 1 }

SproutPRRCurrentEntry ::= SEQUENCE
{
  sproutPRRCurrentScope          OCTET STRING,
  sproutPRRCurrentValue          Unsigned32
}

sproutPRRCurrentScope OBJECT-TYPE
    SYNTAX      OCTET STRING (SIZE(1..64))
    MAX-ACCESS  not-accessible
    STATUS      current
    DESCRIPTION "Statistic scope - should always take the value: node."
    ::= { sproutPRRCurrentEntry 1 }

sproutPRRCurrentValue OBJECT-TYPE
    SYNTAX      Unsigned32
    MAX-ACCESS  read-only
    STATUS      current
    DESCRIPTION "The current permitted request rate."
    ::= { sproutPRRCurrentEntry 2 }

sproutSCSCFINVITEsCancelledBefore1xxTable OBJECT-TYPE
    SYNTAX SEQUENCE OF SproutSCSCFINVITEsCancelledBefore1xxEntry
    MAX-ACCESS not-accessible
    STATUS current
    DESCRIPTION "Number of INVITE transactions that were cancelled before a 1xx
                 response was seen."
    ::= { sprout 32 }

sproutSCSCFINVITEsCancelledBefore1xxEntry OBJECT-TYPE
    SYNTAX      SproutSCSCFINVITEsCancelledBefore1xxEntry
    MAX-ACCESS  not-accessible
    STATUS      current
    DESCRIPTION "The number of INVITE transactions that were cancelled before a
                 1xx response was seen."
    INDEX       { sproutSCSCFINVITEsCancelledBefore1xxScope }
    ::= { sproutSCSCFINVITEsCancelledBefore1xxTable 1 }

SproutSCSCFINVITEsCancelledBefore1xxEntry ::= SEQUENCE
{
  sproutSCSCFINVITEsCancelledBefore1xxScope        INTEGER,
  sproutSCSCFINVITEsCancelledBefore1xxCount        Unsigned32
}

sproutSCSCFINVITEsCancelledBefore1xxScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFINVITEsCancelledBefore1xxEntry 1 }

sproutSCSCFINVITEsCancelledBefore1xxCount OBJECT-TYPE
    SYNTAX      Unsigned32
    MAX-ACCESS  read-only
    STATUS      current
    DESCRIPTION "The number of INVITE transactions that were cancelled before a
                 1xx response was seen."
    ::= { sproutSCSCFINVITEsCancelledBefore1xxEntry 2 }

sproutSCSCFINVITEsCancelledAfter1xxTable OBJECT-TYPE
    SYNTAX SEQUENCE OF SproutSCSCFINVITEsCancelledAfter1xxEntry
    MAX-ACCESS not-accessible
    STATUS current
    DESCRIPTION "Number of INVITE transactions that were cancelled before a 1xx
                 response was seen."
    ::= { sprout 33 }

sproutSCSCFINVITEsCancelledAfter1xxEntry OBJECT-TYPE
    SYNTAX      SproutSCSCFINVITEsCancelledAfter1xxEntry
    MAX-ACCESS  not-accessible
    STATUS      current
    DESCRIPTION "The number of INVITE transactions that were cancelled after a
                 1xx response was seen."
    INDEX       { sproutSCSCFINVITEsCancelledAfter1xxScope }
    ::= { sproutSCSCFINVITEsCancelledAfter1xxTable 1 }

SproutSCSCFINVITEsCancelledAfter1xxEntry ::= SEQUENCE
{
  sproutSCSCFINVITEsCancelledAfter1xxScope        INTEGER,
  sproutSCSCFINVITEsCancelledAfter1xxCount        Unsigned32
}

sproutSCSCFINVITEsCancelledAfter1xxScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFINVITEsCancelledAfter1xxEntry 1 }

sproutSCSCFINVITEsCancelledAfter1xxCount OBJECT-TYPE
    SYNTAX      Unsigned32
    MAX-ACCESS  read-only
    STATUS      current
    DESCRIPTION "The number of INVITE transactions that were cancelled after a
                 1xx response was seen."
    ::= { sproutSCSCFINVITEsCancelledAfter1xxEntry 2 }

sproutSCSCFAudioSessionSetupTimeTable OBJECT-TYPE
    SYNTAX SEQUENCE OF SproutSCSCFAudioSessionSetupTimeEntry
    MAX-ACCESS not-accessible
    STATUS current
    DESCRIPTION "Stats for audio calls regarding the time between originating
                 INVITEs being received and first successful response (e.g. 180
                 RINGING or 200 OK).  For the purposes of these stats a call is
                 considered to be an audio call if video is not specified in the
                 SDP on the initial INVITE."
    ::= { sprout 34 }

sproutSCSCFAudioSessionSetupTimeEntry OBJECT-TYPE
    SYNTAX      SproutSCSCFAudioSessionSetupTimeEntry
    MAX-ACCESS  not-accessible
    STATUS      current
    DESCRIPTION "The average, variance, LWM and HWM of audio session setup time"
    INDEX       { sproutSCSCFAudioSessionSetupTimeScope }
    ::= { sproutSCSCFAudioSessionSetupTimeTable 1 }

SproutSCSCFAudioSessionSetupTimeEntry ::= SEQUENCE
{
  sproutSCSCFAudioSessionSetupTimeScope          INTEGER,
  sproutSCSCFAudioSessionSetupTimeAverage        Unsigned32,
  sproutSCSCFAudioSessionSetupTimeVariance       Unsigned32,
  sproutSCSCFAudioSessionSetupTimeHWM            Unsigned32,
  sproutSCSCFAudioSessionSetupTimeLWM            Unsigned32,
  sproutSCSCFAudioSessionSetupTimeCount          Unsigned32
}

sproutSCSCFAudioSessionSetupTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFAudioSessionSetupTimeEntry 1 }

sproutSCSCFAudioSessionSetupTimeAverage OBJECT-TYPE
    SYNTAX      Unsigned32
    MAX-ACCESS  read-only
    STATUS      current
    DESCRIPTION "The average audio session setup time over the period."
    ::= { sproutSCSCFAudioSessionSetupTimeEntry 2 }

sproutSCSCFAudioSessionSetupTimeVariance OBJECT-TYPE
    SYNTAX      Unsigned32
    MAX-ACCESS  read-only
    STATUS      current
    DESCRIPTION "The variance of the audio session setup time over the period."
    ::= { sproutSCSCFAudioSessionSetupTimeEntry 3 }

sproutSCSCFAudioSessionSetupTimeHWM OBJECT-TYPE
    SYNTAX      Unsigned32
    MAX-ACCESS  read-only
    STATUS      current
    DESCRIPTION "The highest audio session setup time over the period."
    ::= { sproutSCSCFAudioSessionSetupTimeEntry 4 }

sproutSCSCFAudioSessionSetupTimeLWM OBJECT-TYPE
    SYNTAX      Unsigned32
    MAX-ACCESS  read-only
    STATUS      current
    DESCRIPTION "The lowest audio session setup time over the period."
    ::= { sproutSCSCFAudioSessionSetupTimeEntry 5 }

sproutSCSCFAudioSessionSetupTimeCount OBJECT-TYPE
    SYNTAX      Unsigned32
    MAX-ACCESS  read-only
    STATUS      current
    DESCRIPTION "The total originating INVITEs for audio calls received over the
                 period."
    ::= { sproutSCSCFAudioSessionSetupTimeEntry 6 }

sproutSCSCFVideoSessionSetupTimeTable OBJECT-TYPE
    SYNTAX SEQUENCE OF SproutSCSCFVideoSessionSetupTimeEntry
    MAX-ACCESS not-accessible
    STATUS current
    DESCRIPTION "Stats for video calls regarding the time between originating
                 INVITEs being received and first successful response (e.g. 180
                 RINGING or 200 OK).  For the purposes of these stats a call is
                 considered to be a video call if video is specified in the SDP
                 on the initial INVITE (irrespective of whether the call
                 actually ends up using video)."
    ::= { sprout 35 }

sproutSCSCFVideoSessionSetupTimeEntry OBJECT-TYPE
    SYNTAX      SproutSCSCFVideoSessionSetupTimeEntry
    MAX-ACCESS  not-accessible
    STATUS      current
    DESCRIPTION "The average, variance, LWM and HWM of video session setup time"
    INDEX       { sproutSCSCFVideoSessionSetupTimeScope }
    ::= { sproutSCSCFVideoSessionSetupTimeTable 1 }

SproutSCSCFVideoSessionSetupTimeEntry ::= SEQUENCE
{
  sproutSCSCFVideoSessionSetupTimeScope          INTEGER,
  sproutSCSCFVideoSessionSetupTimeAverage        Unsigned32,
  sproutSCSCFVideoSessionSetupTimeVariance       Unsigned32,
  sproutSCSCFVideoSessionSetupTimeHWM            Unsigned32,
  sproutSCSCFVideoSessionSetupTimeLWM            Unsigned32,
  sproutSCSCFVideoSessionSetupTimeCount          Unsigned32
}

sproutSCSCFVideoSessionSetupTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFVideoSessionSetupTimeEntry 1 }

sproutSCSCFVideoSessionSetupTimeAverage OBJECT-TYPE
    SYNTAX      Unsigned32
    MAX-ACCESS  read-only
    STATUS      current
    DESCRIPTION "The average video session setup time over the period."
    ::= { sproutSCSCFVideoSessionSetupTimeEntry 2 }

sproutSCSCFVideoSessionSetupTimeVariance OBJECT-TYPE
    SYNTAX      Unsigned32
    MAX-ACCESS  read-only
    STATUS      current
    DESCRIPTION "The variance of the video session setup time over the period."
    ::= { sproutSCSCFVideoSessionSetupTimeEntry 3 }

sproutSCSCFVideoSessionSetupTimeHWM OBJECT-TYPE
    SYNTAX      Unsigned32
    MAX-ACCESS  read-only
    STATUS      current
    DESCRIPTION "The highest video session setup time over the period."
    ::= { sproutSCSCFVideoSessionSetupTimeEntry 4 }

sproutSCSCFVideoSessionSetupTimeLWM OBJECT-TYPE
    SYNTAX      Unsigned32
    MAX-ACCESS  read-only
    STATUS      current
    DESCRIPTION "The lowest video session setup time over the period."
    ::= { sproutSCSCFVideoSessionSetupTimeEntry 5 }

sproutSCSCFVideoSessionSetupTimeCount OBJECT-TYPE
    SYNTAX      Unsigned32
    MAX-ACCESS  read-only
    STATUS      current
    DESCRIPTION "The total originating INVITEs for video calls received over the
                 period."
    ::= { sproutSCSCFVideoSessionSetupTimeEntry 6 }

sproutICSCFSessionEstablishmentTable OBJECT-TYPE
    SYNTAX SEQUENCE OF SproutICSCFSessionEstablishmentEntry
    MAX-ACCESS not-accessible
    STATUS current
    DESCRIPTION "Stats regarding attempts to establish terminating sessions at
                 the I-CSCF.
                 Each INVITE received by the I-CSCF (from the originating
                 S-CSCF) is counted as a terminating session attempt.
                 Such an attempt is considered successful if the I-CSCF
                 responds with a 180 RINGING or 200 OK."
    ::= { sprout 36 }

sproutICSCFSessionEstablishmentEntry OBJECT-TYPE
    SYNTAX      SproutICSCFSessionEstablishmentEntry
    MAX-ACCESS  not-accessible
    STATUS      current
    DESCRIPTION "The number of attempted, successful and failed terminating
                 sessions, and (for convenience) the percentage of terminating
                 session attempts that were successful."
    INDEX       { sproutICSCFSessionEstablishmentScope }
    ::= { sproutICSCFSessionEstablishmentTable 1 }

SproutICSCFSessionEstablishmentEntry ::= SEQUENCE
{
  sproutICSCFSessionEstablishmentScope          INTEGER,
  sproutICSCFSessionEstablishmentAttempts       Unsigned32,
  sproutICSCFSessionEstablishmentSuccesses      Unsigned32,
  sproutICSCFSessionEstablishmentFailures       Unsigned32,
  sproutICSCFSessionEstablishmentSuccessPercent Unsigned32
}

sproutICSCFSessionEstablishmentScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutICSCFSessionEstablishmentEntry 1 }

sproutICSCFSessionEstablishmentAttempts OBJECT-TYPE
    SYNTAX      Unsigned32
    MAX-ACCESS  read-only
    STATUS      current
    DESCRIPTION "The number of terminating session attempts over the period."
    ::= { sproutICSCFSessionEstablishmentEntry 2 }

sproutICSCFSessionEstablishmentSuccesses OBJECT-TYPE
    SYNTAX      Unsigned32
    MAX-ACCESS  read-only
    STATUS      current
    DESCRIPTION "The number of successful terminating session attempts over the
                 period."
    ::= { sproutICSCFSessionEstablishmentEntry 3 }

sproutICSCFSessionEstablishmentFailures OBJECT-TYPE
    SYNTAX      Unsigned32
    MAX-ACCESS  read-only
    STATUS      current
    DESCRIPTION "The number of failed terminating session attempts over the
                 period. Note that 3xx responses are counted as session
                 establishment failures."
    ::= { sproutICSCFSessionEstablishmentEntry 4 }

sproutICSCFSessionEstablishmentSuccessPercent OBJECT-TYPE
    SYNTAX      Unsigned32
    UNITS       "/ 10000 %"
    MAX-ACCESS  read-only
    STATUS      current
    DESCRIPTION "The percentage of terminating session attempts over the
                 period that were successful. Reported in units of ten
                 thousandths of a percentage point. When there are zero
                 attempts made, the value will be 1000000 to represent 100%."
    ::= { sproutICSCFSessionEstablishmentEntry 5 }

sproutICSCFSessionEstablishmentNetworkTable OBJECT-TYPE
    SYNTAX SEQUENCE OF SproutICSCFSessionEstablishmentNetworkEntry
    MAX-ACCESS not-accessible
    STATUS current
    DESCRIPTION "Stats regarding attempts to establish terminating sessions at
                 the I-CSCF.  This provides stats about the same set of events
                 as the sproutICSCFSessionEstablishmentTable, but this time
                 only considering whether the request was successful from a
                 network perspective.
                 Each INVITE received by the I-CSCF (from the originating
                 S-CSCF) is counted as a terminating session attempt.
                 Such an attempt is considered successful from a network
                 perspective if either
                 - the I-CSCF responds with a 180 RINGING or 200 OK
                 - the session is canceled by the originating party before
                   being established
                 - the session is rejected with 486 BUSY HERE, 600 BUSY
                   EVERYWHERE, 404 NOT FOUND or 484 ADDRESS INCOMPLETE."
    ::= { sprout 37 }

sproutICSCFSessionEstablishmentNetworkEntry OBJECT-TYPE
    SYNTAX      SproutICSCFSessionEstablishmentNetworkEntry
    MAX-ACCESS  not-accessible
    STATUS      current
    DESCRIPTION "The number of attempted, successful and failed terminating
                 sessions, and (for convenience) the percentage of terminating
                 session attempts that were successful."
    INDEX       { sproutICSCFSessionEstablishmentNetworkScope }
    ::= { sproutICSCFSessionEstablishmentNetworkTable 1 }

SproutICSCFSessionEstablishmentNetworkEntry ::= SEQUENCE
{
  sproutICSCFSessionEstablishmentNetworkScope          INTEGER,
  sproutICSCFSessionEstablishmentNetworkAttempts       Unsigned32,
  sproutICSCFSessionEstablishmentNetworkSuccesses      Unsigned32,
  sproutICSCFSessionEstablishmentNetworkFailures       Unsigned32,
  sproutICSCFSessionEstablishmentNetworkSuccessPercent Unsigned32
}

sproutICSCFSessionEstablishmentNetworkScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutICSCFSessionEstablishmentNetworkEntry 1 }

sproutICSCFSessionEstablishmentNetworkAttempts OBJECT-TYPE
    SYNTAX      Unsigned32
    MAX-ACCESS  read-only
    STATUS      current
    DESCRIPTION "The number of terminating session attempts over the period."
    ::= { sproutICSCFSessionEstablishmentNetworkEntry 2 }

sproutICSCFSessionEstablishmentNetworkSuccesses OBJECT-TYPE
    SYNTAX      Unsigned32
    MAX-ACCESS  read-only
    STATUS      current
    DESCRIPTION "The number of terminating session attempts over the
                 period that were successful from a network perspective.
                 Reported in units of ten thousandths of a percentage point.
                 When there are zero attempts made the value will be
                 1000000 to represent 100%."
    ::= { sproutICSCFSessionEstablishmentNetworkEntry 3 }

sproutICSCFSessionEstablishmentNetworkFailures OBJECT-TYPE
    SYNTAX      Unsigned32
    MAX-ACCESS  read-only
    STATUS      current
    DESCRIPTION "The number of terminating session attempts over the
                 period that failed due to the network."
    ::= { sproutICSCFSessionEstablishmentNetworkEntry 4 }

sproutICSCFSessionEstablishmentNetworkSuccessPercent OBJECT-TYPE
    SYNTAX      Unsigned32
    UNITS       "/ 10000 %"
    MAX-ACCESS  read-only
    STATUS      current
    DESCRIPTION "The percentage of terminating session attempts over the
                 period that were successful from a network perspective.
                 Reported in units of ten thousandths of a percentage point.
                 When there are zero attempts made the value will be
                 1000000 to represent 100%."
    ::= { sproutICSCFSessionEstablishmentNetworkEntry 5 }

sproutSCSCFINVITEsForkedTable OBJECT-TYPE
    SYNTAX SEQUENCE OF SproutSCSCFINVITEsForkedEntry
    MAX-ACCESS not-accessible
    STATUS current
    DESCRIPTION "Number of extra INVITEs created due to multiple registrations."
    ::= { sprout 38 }

sproutSCSCFINVITEsForkedEntry OBJECT-TYPE
    SYNTAX      SproutSCSCFINVITEsForkedEntry
    MAX-ACCESS  not-accessible
    STATUS      current
    DESCRIPTION "The number of extra INVITEs created due to multiple registrations."
    INDEX       { sproutSCSCFINVITEsForkedScope }
    ::= { sproutSCSCFINVITEsForkedTable 1 }

SproutSCSCFINVITEsForkedEntry ::= SEQUENCE
{
  sproutSCSCFINVITEsForkedScope        INTEGER,
  sproutSCSCFINVITEsForkedCount        Unsigned32
}

sproutSCSCFINVITEsForkedScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFINVITEsForkedEntry 1 }

sproutSCSCFINVITEsForkedCount OBJECT-TYPE
    SYNTAX      Unsigned32
    MAX-ACCESS  read-only
    STATUS      current
    DESCRIPTION "The number of extra INVITEs created due to multiple registrations."
    ::= { sproutSCSCFINVITEsForkedEntry 2 }

sproutSCSCFINVITEsNoMatchingDefaultIFCsTable OBJECT-TYPE
    SYNTAX SEQUENCE OF SproutSCSCFINVITEsNoMatchingDefaultIFCsEntry
    MAX-ACCESS not-accessible
    STATUS current
    DESCRIPTION "Number of initial requests that attempted to use default IFCs but had no matching ones."
    ::= { sprout 39 }

sproutSCSCFINVITEsNoMatchingDefaultIFCsEntry OBJECT-TYPE
    SYNTAX      SproutSCSCFINVITEsNoMatchingDefaultIFCsEntry
    MAX-ACCESS  not-accessible
    STATUS      current
    DESCRIPTION "Number of initial requests that attempted to use default IFCs but had no matching ones."
    INDEX       { sproutSCSCFINVITEsNoMatchingDefaultIFCsScope }
    ::= { sproutSCSCFINVITEsNoMatchingDefaultIFCsTable 1 }

SproutSCSCFINVITEsNoMatchingDefaultIFCsEntry ::= SEQUENCE
{
  sproutSCSCFINVITEsNoMatchingDefaultIFCsScope        INTEGER,
  sproutSCSCFINVITEsNoMatchingDefaultIFCsCount        Unsigned32
}

sproutSCSCFINVITEsNoMatchingDefaultIFCsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFINVITEsNoMatchingDefaultIFCsEntry 1 }

sproutSCSCFINVITEsNoMatchingDefaultIFCsCount OBJECT-TYPE
    SYNTAX      Unsigned32
    MAX-ACCESS  read-only
    STATUS      current
    DESCRIPTION "Number of initial requests that attempted to use default IFCs but had no matching ones."
    ::= { sproutSCSCFINVITEsNoMatchingDefaultIFCsEntry 2 }

sproutSCSCFINVITEsNoSharedIFCsSetTable OBJECT-TYPE
    SYNTAX SEQUENCE OF SproutSCSCFINVITEsNoSharedIFCsSetEntry
    MAX-ACCESS not-accessible
    STATUS current
    DESCRIPTION "Number of shared IFC set IDs retrieved from the HSS where the S-CSCF has no matching set of IFCs."
    ::= { sprout 40 }

sproutSCSCFINVITEsNoSharedIFCsSetEntry OBJECT-TYPE
    SYNTAX      SproutSCSCFINVITEsNoSharedIFCsSetEntry
    MAX-ACCESS  not-accessible
    STATUS      current
    DESCRIPTION "Number of shared IFCs set IDS retrieved from the HSS where the S-CSCF has no matching set of IFCs."
    INDEX       { sproutSCSCFINVITEsNoSharedIFCsSetScope }
    ::= { sproutSCSCFINVITEsNoSharedIFCsSetTable 1 }

SproutSCSCFINVITEsNoSharedIFCsSetEntry ::= SEQUENCE
{
  sproutSCSCFINVITEsNoSharedIFCsSetScope        INTEGER,
  sproutSCSCFINVITEsNoSharedIFCsSetCount        Unsigned32
}

sproutSCSCFINVITEsNoSharedIFCsSetScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFINVITEsNoSharedIFCsSetEntry 1 }

sproutSCSCFINVITEsNoSharedIFCsSetCount OBJECT-TYPE
    SYNTAX      Unsigned32
    MAX-ACCESS  read-only
    STATUS      current
    DESCRIPTION "Number of shared IFCs set IDS retrieved from the HSS where the S-CSCF has no matching set of IFCs."
    ::= { sproutSCSCFINVITEsNoSharedIFCsSetEntry 2 }

sproutSCSCFINVITEsNoMatchingIFCsTable OBJECT-TYPE
    SYNTAX SEQUENCE OF SproutSCSCFINVITEsNoMatchingIFCsEntry
    MAX-ACCESS not-accessible
    STATUS current
    DESCRIPTION "Number of initial requests that had no matching IFCs to apply."
    ::= { sprout 41 }

sproutSCSCFINVITEsNoMatchingIFCsEntry OBJECT-TYPE
    SYNTAX      SproutSCSCFINVITEsNoMatchingIFCsEntry
    MAX-ACCESS  not-accessible
    STATUS      current
    DESCRIPTION "Number of initial requests that had no matching IFCs to apply."
    INDEX       { sproutSCSCFINVITEsNoMatchingIFCsScope }
    ::= { sproutSCSCFINVITEsNoMatchingIFCsTable 1 }

SproutSCSCFINVITEsNoMatchingIFCsEntry ::= SEQUENCE
{
  sproutSCSCFINVITEsNoMatchingIFCsScope        INTEGER,
  sproutSCSCFINVITEsNoMatchingIFCsCount        Unsigned32
}

sproutSCSCFINVITEsNoMatchingIFCsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFINVITEsNoMatchingIFCsEntry 1 }

sproutSCSCFINVITEsNoMatchingIFCsCount OBJECT-TYPE
    SYNTAX      Unsigned32
    MAX-ACCESS  read-only
    STATUS      current
    DESCRIPTION "Number of initial requests that had no matching IFCs to apply."
    ::= { sproutSCSCFINVITEsNoMatchingIFCsEntry 2 }

sproutSCSCFBarredRequestsTable OBJECT-TYPE
    SYNTAX SEQUENCE OF SproutSCSCFBarredRequestsEntry
    MAX-ACCESS not-accessible
    STATUS current
    DESCRIPTION "Number of requests rejected because an identity was barred."
    ::= { sprout 42 }

sproutSCSCFBarredRequestsEntry OBJECT-TYPE
    SYNTAX      SproutSCSCFBarredRequestsEntry
    MAX-ACCESS  not-accessible
    STATUS      current
    DESCRIPTION "Number of requests rejected because an identity was barred."
    INDEX       { sproutSCSCFBarredRequestsScope }
    ::= { sproutSCSCFBarredRequestsTable 1 }

SproutSCSCFBarredRequestsEntry ::= SEQUENCE
{
  sproutSCSCFBarredRequestsScope        INTEGER,
  sproutSCSCFBarredRequestsCount        Unsigned32
}

sproutSCSCFBarredRequestsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutSCSCFBarredRequestsEntry 1 }

sproutSCSCFBarredRequestsCount OBJECT-TYPE
    SYNTAX      Unsigned32
    MAX-ACCESS  read-only
    STATUS      current
    DESCRIPTION "Number of requests rejected because an identity was barred."
    ::= { sproutSCSCFBarredRequestsEntry 2 }

sproutGroup OBJECT-GROUP
    OBJECTS {
      sproutLatencyAverage,
      sproutLatencyVariance,
      sproutLatencyHWM,
      sproutLatencyLWM,
      sproutLatencyCount,
      sproutHomesteadConnectionCount,
      sproutHomesteadLatencyAverage,
      sproutHomesteadLatencyVariance,
      sproutHomesteadLatencyHWM,
      sproutHomesteadLatencyLWM,
      sproutHomesteadLatencyCount,
      sproutMARLatencyAverage,
      sproutMARLatencyVariance,
      sproutMARLatencyHWM,
      sproutMARLatencyLWM,
      sproutMARLatencyCount,
      sproutSARLatencyAverage,
      sproutSARLatencyVariance,
      sproutSARLatencyHWM,
      sproutSARLatencyLWM,
      sproutSARLatencyCount,
      sproutUARLatencyAverage,
      sproutUARLatencyVariance,
      sproutUARLatencyHWM,
      sproutUARLatencyLWM,
      sproutUARLatencyCount,
      sproutLIRLatencyAverage,
      sproutLIRLatencyVariance,
      sproutLIRLatencyHWM,
      sproutLIRLatencyLWM,
      sproutLIRLatencyCount,
      sproutIncomingRequestsCount,
      sproutRejectedOverloadCount,
      sproutQueueSizeAverage,
      sproutQueueSizeVariance,
      sproutQueueSizeHWM,
      sproutQueueSizeLWM,
      sproutQueueSizeCount,
      sproutSCSCFInitialRegistrationAttempts,
      sproutSCSCFInitialRegistrationSuccesses,
      sproutSCSCFInitialRegistrationFailures,
      sproutSCSCFInitialRegistrationSuccessPercent,
      sproutSCSCFReRegistrationAttempts,
      sproutSCSCFReRegistrationSuccesses,
      sproutSCSCFReRegistrationFailures,
      sproutSCSCFReRegistrationSuccessPercent,
      sproutSCSCFDeRegistrationAttempts,
      sproutSCSCFDeRegistrationSuccesses,
      sproutSCSCFDeRegistrationFailures,
      sproutSCSCFDeRegistrationSuccessPercent,
      sproutSCSCFThirdPartyInitialRegistrationAttempts,
      sproutSCSCFThirdPartyInitialRegistrationSuccesses,
      sproutSCSCFThirdPartyInitialRegistrationFailures,
      sproutSCSCFThirdPartyInitialRegistrationSuccessPercent,
      sproutSCSCFThirdPartyReRegistrationAttempts,
      sproutSCSCFThirdPartyReRegistrationSuccesses,
      sproutSCSCFThirdPartyReRegistrationFailures,
      sproutSCSCFThirdPartyReRegistrationSuccessPercent,
      sproutSCSCFThirdPartyDeRegistrationAttempts,
      sproutSCSCFThirdPartyDeRegistrationSuccesses,
      sproutSCSCFThirdPartyDeRegistrationFailures,
      sproutSCSCFThirdPartyDeRegistrationSuccessPercent,
      sproutSCSCFSIPDigestAuthenticationAttempts,
      sproutSCSCFSIPDigestAuthenticationSuccesses,
      sproutSCSCFSIPDigestAuthenticationFailures,
      sproutSCSCFSIPDigestAuthenticationSuccessPercent,
      sproutSCSCFAKAAuthenticationAttempts,
      sproutSCSCFAKAAuthenticationSuccesses,
      sproutSCSCFAKAAuthenticationFailures,
      sproutSCSCFAKAAuthenticationSuccessPercent,
      sproutSCSCFNonRegisterAuthenticationAttempts,
      sproutSCSCFNonRegisterAuthenticationSuccesses,
      sproutSCSCFNonRegisterAuthenticationFailures,
      sproutSCSCFNonRegisterAuthenticationSuccessPercent,
      sproutICSCFIncomingSIPTransactionsAttempts,
      sproutICSCFIncomingSIPTransactionsSuccesses,
      sproutICSCFIncomingSIPTransactionsFailures,
      sproutICSCFIncomingSIPTransactionsSuccessPercent,
      sproutICSCFOutgoingSIPTransactionsAttempts,
      sproutICSCFOutgoingSIPTransactionsSuccesses,
      sproutICSCFOutgoingSIPTransactionsFailures,
      sproutICSCFOutgoingSIPTransactionsSuccessPercent,
      sproutSCSCFIncomingSIPTransactionsAttempts,
      sproutSCSCFIncomingSIPTransactionsSuccesses,
      sproutSCSCFIncomingSIPTransactionsFailures,
      sproutSCSCFIncomingSIPTransactionsSuccessPercent,
      sproutSCSCFOutgoingSIPTransactionsAttempts,
      sproutSCSCFOutgoingSIPTransactionsSuccesses,
      sproutSCSCFOutgoingSIPTransactionsFailures,
      sproutSCSCFOutgoingSIPTransactionsSuccessPercent,
      sproutSCSCFRequestsRoutedByPreloadedRouteCount,
      sproutPRRAverage,
      sproutPRRVariance,
      sproutPRRHWM,
      sproutPRRLWM,
      sproutPRRCount,
      sproutSmoothedLatencyValue,
      sproutTargetLatencyValue,
      sproutPenaltiesValue,
      sproutPRRCurrentValue,
      sproutSCSCFINVITEsCancelledBefore1xxCount,
      sproutSCSCFINVITEsCancelledAfter1xxCount,
      sproutSCSCFAudioSessionSetupTimeAverage,
      sproutSCSCFAudioSessionSetupTimeVariance,
      sproutSCSCFAudioSessionSetupTimeHWM,
      sproutSCSCFAudioSessionSetupTimeLWM,
      sproutSCSCFAudioSessionSetupTimeCount,
      sproutSCSCFVideoSessionSetupTimeAverage,
      sproutSCSCFVideoSessionSetupTimeVariance,
      sproutSCSCFVideoSessionSetupTimeHWM,
      sproutSCSCFVideoSessionSetupTimeLWM,
      sproutSCSCFVideoSessionSetupTimeCount,
      sproutICSCFSessionEstablishmentAttempts,
      sproutICSCFSessionEstablishmentSuccesses,
      sproutICSCFSessionEstablishmentFailures,
      sproutICSCFSessionEstablishmentSuccessPercent,
      sproutICSCFSessionEstablishmentNetworkAttempts,
      sproutICSCFSessionEstablishmentNetworkSuccesses,
      sproutICSCFSessionEstablishmentNetworkFailures,
      sproutICSCFSessionEstablishmentNetworkSuccessPercent,
      sproutSCSCFINVITEsForkedCount,
      sproutSCSCFINVITEsNoMatchingDefaultIFCsCount,
      sproutSCSCFINVITEsNoSharedIFCsSetCount,
      sproutSCSCFINVITEsNoMatchingIFCsCount,
      sproutSCSCFBarredRequestsCount
    }
    STATUS      current
    DESCRIPTION "Statistics exposed by Sprout"
    ::= { commonClearwaterObjectGroups 2 }

-- Homestead entries

homesteadLatencyTable OBJECT-TYPE
    SYNTAX SEQUENCE OF HomesteadLatencyEntry
    MAX-ACCESS not-accessible
    STATUS current
    DESCRIPTION "Latency of HTTP requests handled by this Homestead
                 over the given period.  Latency measured in
                 microseconds"
    ::= { homestead 1 }

homesteadLatencyEntry OBJECT-TYPE
    SYNTAX      HomesteadLatencyEntry
    MAX-ACCESS  not-accessible
    STATUS      current
    DESCRIPTION "The average, variance, LWM and HWM of HTTP request
                 latency"
    INDEX       { homesteadLatencyScope }
    ::= { homesteadLatencyTable 1 }

HomesteadLatencyEntry ::= SEQUENCE
{
  homesteadLatencyScope          INTEGER,
  homesteadLatencyAverage        Unsigned32,
  homesteadLatencyVariance       Unsigned32,
  homesteadLatencyHWM            Unsigned32,
  homesteadLatencyLWM            Unsigned32,
  homesteadLatencyCount          Unsigned32
}

homesteadLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadLatencyEntry 1 }

homesteadLatencyAverage OBJECT-TYPE
    SYNTAX      Unsigned32
    MAX-ACCESS  read-only
    STATUS      current
    DESCRIPTION "The average latency over the period."
    ::= { homesteadLatencyEntry 2 }

homesteadLatencyVariance OBJECT-TYPE
    SYNTAX      Unsigned32
    MAX-ACCESS  read-only
    STATUS      current
    DESCRIPTION "The variance of the latency over the period."
    ::= { homesteadLatencyEntry 3 }

homesteadLatencyHWM OBJECT-TYPE
    SYNTAX      Unsigned32
    MAX-ACCESS  read-only
    STATUS      current
    DESCRIPTION "The highest latency over the period."
    ::= { homesteadLatencyEntry 4 }

homesteadLatencyLWM OBJECT-TYPE
    SYNTAX      Unsigned32
    MAX-ACCESS  read-only
    STATUS      current
    DESCRIPTION "The lowest latency over the period."
    ::= { homesteadLatencyEntry 5 }

homesteadLatencyCount OBJECT-TYPE
    SYNTAX      Unsigned32
    MAX-ACCESS  read-only
    STATUS      current
    DESCRIPTION "The total requests over the period."
    ::= { homesteadLatencyEntry 6 }

homesteadHSSLatencyTable OBJECT-TYPE
    SYNTAX SEQUENCE OF HomesteadHSSLatencyEntry
    MAX-ACCESS not-accessible
    STATUS current
    DESCRIPTION "Latency of HSS requests made by this Homestead
                 over the given period.  Latency measured in
                 microseconds"
    ::= { homestead 2 }

homesteadHSSLatencyEntry OBJECT-TYPE
    SYNTAX      HomesteadHSSLatencyEntry
    MAX-ACCESS  not-accessible
    STATUS      current
    DESCRIPTION "The average, variance, LWM and HWM of HSS request
                 latency"
    INDEX       { homesteadHSSLatencyScope }
    ::= { homesteadHSSLatencyTable 1 }

HomesteadHSSLatencyEntry ::= SEQUENCE
{
  homesteadHSSLatencyScope          INTEGER,
  homesteadHSSLatencyAverage        Unsigned32,
  homesteadHSSLatencyVariance       Unsigned32,
  homesteadHSSLatencyHWM            Unsigned32,
  homesteadHSSLatencyLWM            Unsigned32,
  homesteadHSSLatencyCount          Unsigned32
}

homesteadHSSLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadHSSLatencyEntry 1 }

homesteadHSSLatencyAverage OBJECT-TYPE
    SYNTAX      Unsigned32
    MAX-ACCESS  read-only
    STATUS      current
    DESCRIPTION "The average latency over the period."
    ::= { homesteadHSSLatencyEntry 2 }

homesteadHSSLatencyVariance OBJECT-TYPE
    SYNTAX      Unsigned32
    MAX-ACCESS  read-only
    STATUS      current
    DESCRIPTION "The variance of the latency over the period."
    ::= { homesteadHSSLatencyEntry 3 }

homesteadHSSLatencyHWM OBJECT-TYPE
    SYNTAX      Unsigned32
    MAX-ACCESS  read-only
    STATUS      current
    DESCRIPTION "The highest latency over the period."
    ::= { homesteadHSSLatencyEntry 4 }

homesteadHSSLatencyLWM OBJECT-TYPE
    SYNTAX      Unsigned32
    MAX-ACCESS  read-only
    STATUS      current
    DESCRIPTION "The lowest latency over the period."
    ::= { homesteadHSSLatencyEntry 5 }

homesteadHSSLatencyCount OBJECT-TYPE
    SYNTAX      Unsigned32
    MAX-ACCESS  read-only
    STATUS      current
    DESCRIPTION "The total requests over the period."
    ::= { homesteadHSSLatencyEntry 6 }

homesteadCacheLatencyTable OBJECT-TYPE
    SYNTAX SEQUENCE OF HomesteadCacheLatencyEntry
    MAX-ACCESS not-accessible
    STATUS current
    DESCRIPTION "Latency of cache requests made by this Homestead
                 over a the given period.  Latency measured in
                 microseconds"
    ::= { homestead 3 }

homesteadCacheLatencyEntry OBJECT-TYPE
    SYNTAX      HomesteadCacheLatencyEntry
    MAX-ACCESS  not-accessible
    STATUS      current
    DESCRIPTION "The average, variance, LWM and HWM of request
                 latency"
    INDEX       { homesteadCacheLatencyScope }
    ::= { homesteadCacheLatencyTable 1 }

HomesteadCacheLatencyEntry ::= SEQUENCE
{
  homesteadCacheLatencyScope          INTEGER,
  homesteadCacheLatencyAverage        Unsigned32,
  homesteadCacheLatencyVariance       Unsigned32,
  homesteadCacheLatencyHWM            Unsigned32,
  homesteadCacheLatencyLWM            Unsigned32,
  homesteadCacheLatencyCount          Unsigned32
}

homesteadCacheLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCacheLatencyEntry 1 }

homesteadCacheLatencyAverage OBJECT-TYPE
    SYNTAX      Unsigned32
    MAX-ACCESS  read-only
    STATUS      current
    DESCRIPTION "The average latency over the period."
    ::= { homesteadCacheLatencyEntry 2 }

homesteadCacheLatencyVariance OBJECT-TYPE
    SYNTAX      Unsigned32
    MAX-ACCESS  read-only
    STATUS      current
    DESCRIPTION "The variance of the latency over the period."
    ::= { homesteadCacheLatencyEntry 3 }

homesteadCacheLatencyHWM OBJECT-TYPE
    SYNTAX      Unsigned32
    MAX-ACCESS  read-only
    STATUS      current
    DESCRIPTION "The highest latency over the period."
    ::= { homesteadCacheLatencyEntry 4 }

homesteadCacheLatencyLWM OBJECT-TYPE
    SYNTAX      Unsigned32
    MAX-ACCESS  read-only
    STATUS      current
    DESCRIPTION "The lowest latency over the period."
    ::= { homesteadCacheLatencyEntry 5 }

homesteadCacheLatencyCount OBJECT-TYPE
    SYNTAX      Unsigned32
    MAX-ACCESS  read-only
    STATUS      current
    DESCRIPTION "The total requests over the period."
    ::= { homesteadCacheLatencyEntry 6 }

homesteadDigestLatencyTable OBJECT-TYPE
    SYNTAX SEQUENCE OF HomesteadDigestLatencyEntry
    MAX-ACCESS not-accessible
    STATUS current
    DESCRIPTION "Latency of requests for Digests made by this Homestead
                 over the given period.  Latency measured in
                 microseconds"
    ::= { homestead 4 }

homesteadDigestLatencyEntry OBJECT-TYPE
    SYNTAX      HomesteadDigestLatencyEntry
    MAX-ACCESS  not-accessible
    STATUS      current
    DESCRIPTION "The average, variance, LWM and HWM of request
                 latency"
    INDEX       { homesteadDigestLatencyScope }
    ::= { homesteadDigestLatencyTable 1 }

HomesteadDigestLatencyEntry ::= SEQUENCE
{
  homesteadDigestLatencyScope          INTEGER,
  homesteadDigestLatencyAverage        Unsigned32,
  homesteadDigestLatencyVariance       Unsigned32,
  homesteadDigestLatencyHWM            Unsigned32,
  homesteadDigestLatencyLWM            Unsigned32,
  homesteadDigestLatencyCount          Unsigned32
}

homesteadDigestLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadDigestLatencyEntry 1 }

homesteadDigestLatencyAverage OBJECT-TYPE
    SYNTAX      Unsigned32
    MAX-ACCESS  read-only
    STATUS      current
    DESCRIPTION "The average latency over the period."
    ::= { homesteadDigestLatencyEntry 2 }

homesteadDigestLatencyVariance OBJECT-TYPE
    SYNTAX      Unsigned32
    MAX-ACCESS  read-only
    STATUS      current
    DESCRIPTION "The variance of the latency over the period."
    ::= { homesteadDigestLatencyEntry 3 }

homesteadDigestLatencyHWM OBJECT-TYPE
    SYNTAX      Unsigned32
    MAX-ACCESS  read-only
    STATUS      current
    DESCRIPTION "The highest latency over the period."
    ::= { homesteadDigestLatencyEntry 4 }

homesteadDigestLatencyLWM OBJECT-TYPE
    SYNTAX      Unsigned32
    MAX-ACCESS  read-only
    STATUS      current
    DESCRIPTION "The lowest latency over the period."
    ::= { homesteadDigestLatencyEntry 5 }

homesteadDigestLatencyCount OBJECT-TYPE
    SYNTAX      Unsigned32
    MAX-ACCESS  read-only
    STATUS      current
    DESCRIPTION "The total requests over the period."
    ::= { homesteadDigestLatencyEntry 6 }

homesteadSubscriptionLatencyTable OBJECT-TYPE
    SYNTAX SEQUENCE OF HomesteadSubscriptionLatencyEntry
    MAX-ACCESS not-accessible
    STATUS current
    DESCRIPTION "Latency of requests for Subscriptions made by this Homestead
                 over the given period.  Latency measured in
                 microseconds"
    ::= { homestead 5 }

homesteadSubscriptionLatencyEntry OBJECT-TYPE
    SYNTAX      HomesteadSubscriptionLatencyEntry
    MAX-ACCESS  not-accessible
    STATUS      current
    DESCRIPTION "The average, variance, LWM and HWM of request
                 latency"
    INDEX       { homesteadSubscriptionLatencyScope }
    ::= { homesteadSubscriptionLatencyTable 1 }

HomesteadSubscriptionLatencyEntry ::= SEQUENCE
{
  homesteadSubscriptionLatencyScope          INTEGER,
  homesteadSubscriptionLatencyAverage        Unsigned32,
  homesteadSubscriptionLatencyVariance       Unsigned32,
  homesteadSubscriptionLatencyHWM            Unsigned32,
  homesteadSubscriptionLatencyLWM            Unsigned32,
  homesteadSubscriptionLatencyCount          Unsigned32
}

homesteadSubscriptionLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadSubscriptionLatencyEntry 1 }

homesteadSubscriptionLatencyAverage OBJECT-TYPE
    SYNTAX      Unsigned32
    MAX-ACCESS  read-only
    STATUS      current
    DESCRIPTION "The average latency over the period."
    ::= { homesteadSubscriptionLatencyEntry 2 }

homesteadSubscriptionLatencyVariance OBJECT-TYPE
    SYNTAX      Unsigned32
    MAX-ACCESS  read-only
    STATUS      current
    DESCRIPTION "The variance of the latency over the period."
    ::= { homesteadSubscriptionLatencyEntry 3 }

homesteadSubscriptionLatencyHWM OBJECT-TYPE
    SYNTAX      Unsigned32
    MAX-ACCESS  read-only
    STATUS      current
    DESCRIPTION "The highest latency over the period."
    ::= { homesteadSubscriptionLatencyEntry 4 }

homesteadSubscriptionLatencyLWM OBJECT-TYPE
    SYNTAX      Unsigned32
    MAX-ACCESS  read-only
    STATUS      current
    DESCRIPTION "The lowest latency over the period."
    ::= { homesteadSubscriptionLatencyEntry 5 }

homesteadSubscriptionLatencyCount OBJECT-TYPE
    SYNTAX      Unsigned32
    MAX-ACCESS  read-only
    STATUS      current
    DESCRIPTION "The total requests over the period."
    ::= { homesteadSubscriptionLatencyEntry 6 }

homesteadIncomingRequestsTable OBJECT-TYPE
    SYNTAX SEQUENCE OF HomesteadIncomingRequestsEntry
    MAX-ACCESS not-accessible
    STATUS current
    DESCRIPTION "Total number of incoming requests handled by this Homestead
                 over the given period."
    ::= { homestead 6 }

homesteadIncomingRequestsEntry OBJECT-TYPE
    SYNTAX      HomesteadIncomingRequestsEntry
    MAX-ACCESS  not-accessible
    STATUS      current
    DESCRIPTION "The total number of incoming requests"
    INDEX       { homesteadIncomingRequestsScope }
    ::= { homesteadIncomingRequestsTable 1 }

HomesteadIncomingRequestsEntry ::= SEQUENCE
{
  homesteadIncomingRequestsScope          INTEGER,
  homesteadIncomingRequestsCount          Unsigned32
}

homesteadIncomingRequestsScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadIncomingRequestsEntry 1 }

homesteadIncomingRequestsCount OBJECT-TYPE
    SYNTAX      Unsigned32
    MAX-ACCESS  read-only
    STATUS      current
    DESCRIPTION "The total number of incoming requests over the period."
    ::= { homesteadIncomingRequestsEntry 2 }

homesteadRejectedOverloadTable OBJECT-TYPE
    SYNTAX SEQUENCE OF HomesteadRejectedOverloadEntry
    MAX-ACCESS not-accessible
    STATUS current
    DESCRIPTION "Total number of requests rejected due to overload by
                 this Homestead over the given period."
    ::= { homestead 7 }

homesteadRejectedOverloadEntry OBJECT-TYPE
    SYNTAX      HomesteadRejectedOverloadEntry
    MAX-ACCESS  not-accessible
    STATUS      current
    DESCRIPTION "The total number of requests rejected due to overload"
    INDEX       { homesteadRejectedOverloadScope }
    ::= { homesteadRejectedOverloadTable 1 }

HomesteadRejectedOverloadEntry ::= SEQUENCE
{
  homesteadRejectedOverloadScope          INTEGER,
  homesteadRejectedOverloadCount          Unsigned32
}

homesteadRejectedOverloadScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadRejectedOverloadEntry 1 }

homesteadRejectedOverloadCount OBJECT-TYPE
    SYNTAX      Unsigned32
    MAX-ACCESS  read-only
    STATUS      current
    DESCRIPTION "The total number of rejected requests due to overload over the
                 period."
    ::= { homesteadRejectedOverloadEntry 2 }

homesteadDiameterInvalidRealmTable OBJECT-TYPE
    SYNTAX SEQUENCE OF HomesteadDiameterInvalidRealmEntry
    MAX-ACCESS not-accessible
    STATUS current
    DESCRIPTION "The total number of Diameter requests with an invalid Destination-Realm handled by the Homestead
                 over the given period."
    ::= { homestead 8 }

homesteadDiameterInvalidRealmEntry OBJECT-TYPE
    SYNTAX      HomesteadDiameterInvalidRealmEntry
    MAX-ACCESS  not-accessible
    STATUS      current
    DESCRIPTION "The total number of Diameter requests with an invalid Destination-Realm."
    INDEX       { homesteadDiameterInvalidRealmScope }
    ::= { homesteadDiameterInvalidRealmTable 1 }

HomesteadDiameterInvalidRealmEntry ::= SEQUENCE
{
  homesteadDiameterInvalidRealmScope          INTEGER,
  homesteadDiameterInvalidRealmCount          Unsigned32
}

homesteadDiameterInvalidRealmScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadDiameterInvalidRealmEntry 1 }

homesteadDiameterInvalidRealmCount OBJECT-TYPE
    SYNTAX      Unsigned32
    MAX-ACCESS  read-only
    STATUS      current
    DESCRIPTION "The total number of Diameter requests with an invalid Destination-Realm over the period."
    ::= { homesteadDiameterInvalidRealmEntry 2 }

homesteadDiameterInvalidHostTable OBJECT-TYPE
    SYNTAX SEQUENCE OF HomesteadDiameterInvalidHostEntry
    MAX-ACCESS not-accessible
    STATUS current
    DESCRIPTION "The total number of Diameter requests with an invalid Destination-Host handled by the Homestead
                 over the given period."
    ::= { homestead 9 }

homesteadDiameterInvalidHostEntry OBJECT-TYPE
    SYNTAX      HomesteadDiameterInvalidHostEntry
    MAX-ACCESS  not-accessible
    STATUS      current
    DESCRIPTION "The total number of Diameter requests with an invalid Destination-Host."
    INDEX       { homesteadDiameterInvalidHostScope }
    ::= { homesteadDiameterInvalidHostTable 1 }

HomesteadDiameterInvalidHostEntry ::= SEQUENCE
{
  homesteadDiameterInvalidHostScope          INTEGER,
  homesteadDiameterInvalidHostCount          Unsigned32
}

homesteadDiameterInvalidHostScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadDiameterInvalidHostEntry 1 }

homesteadDiameterInvalidHostCount OBJECT-TYPE
    SYNTAX      Unsigned32
    MAX-ACCESS  read-only
    STATUS      current
    DESCRIPTION "The total number of Diameter requests with an invalid Destination-Host over the period."
    ::= { homesteadDiameterInvalidHostEntry 2 }

homesteadCxMARResultsTable OBJECT-TYPE
    SYNTAX SEQUENCE OF HomesteadCxMARResultsEntry
    MAX-ACCESS not-accessible
    STATUS current
    DESCRIPTION "The number of MARs sent over the Cx interface indexed by
                 result-code"
    ::= { homestead 10 }

homesteadCxMARResultsEntry OBJECT-TYPE
    SYNTAX       HomesteadCxMARResultsEntry
    MAX-ACCESS   not-accessible
    STATUS       current
    DESCRIPTION  "The number of MARs sent over the Cx interface"
    INDEX        { homesteadCxMARResultsTimeScope,
                   homesteadCxMARResultsDiameterAppIdScope,
                   homesteadCxMARResultsResultCodeScope }
    ::= { homesteadCxMARResultsTable 1 }

HomesteadCxMARResultsEntry ::= SEQUENCE
{
  homesteadCxMARResultsTimeScope           INTEGER,
  homesteadCxMARResultsDiameterAppIdScope  INTEGER,
  homesteadCxMARResultsResultCodeScope     Unsigned32,
  homesteadCxMARResultsCount               Unsigned32
}

homesteadCxMARResultsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCxMARResultsEntry 1 }

homesteadCxMARResultsDiameterAppIdScope OBJECT-TYPE
    SYNTAX      INTEGER {
                  scopeBase(0),
                  scope3GPP(1),
                  scopeTimeout(2)
                }
    MAX-ACCESS  not-accessible
    STATUS      current
    DESCRIPTION "The Diameter application which the result-code is referring to."
    ::= { homesteadCxMARResultsEntry 2 }

homesteadCxMARResultsResultCodeScope OBJECT-TYPE
    SYNTAX      Unsigned32 (0..6000)
    MAX-ACCESS  not-accessible
    STATUS      current
    DESCRIPTION "The result-code returned in the answer."
    ::= { homesteadCxMARResultsEntry 3 }

homesteadCxMARResultsCount OBJECT-TYPE
    SYNTAX      Unsigned32
    MAX-ACCESS  read-only
    STATUS      current
    DESCRIPTION "The number of times that result-code has been returned as an
                 answer over the time period."
    ::= { homesteadCxMARResultsEntry 4 }

homesteadCxSARResultsTable OBJECT-TYPE
    SYNTAX SEQUENCE OF HomesteadCxSARResultsEntry
    MAX-ACCESS not-accessible
    STATUS current
    DESCRIPTION "The number of SARs sent over the Cx interface indexed by
                 result-code"
    ::= { homestead 11 }

homesteadCxSARResultsEntry OBJECT-TYPE
    SYNTAX       HomesteadCxSARResultsEntry
    MAX-ACCESS   not-accessible
    STATUS       current
    DESCRIPTION  "The number of SARs sent over the Cx interface"
    INDEX        { homesteadCxSARResultsTimeScope,
                   homesteadCxSARResultsDiameterAppIdScope,
                   homesteadCxSARResultsResultCodeScope }
    ::= { homesteadCxSARResultsTable 1 }

HomesteadCxSARResultsEntry ::= SEQUENCE
{
  homesteadCxSARResultsTimeScope           INTEGER,
  homesteadCxSARResultsDiameterAppIdScope  INTEGER,
  homesteadCxSARResultsResultCodeScope     Unsigned32,
  homesteadCxSARResultsCount               Unsigned32
}

homesteadCxSARResultsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCxSARResultsEntry 1 }

homesteadCxSARResultsDiameterAppIdScope OBJECT-TYPE
    SYNTAX      INTEGER {
                  scopeBase(0),
                  scope3GPP(1),
                  scopeTimeout(2)
                }
    MAX-ACCESS  not-accessible
    STATUS      current
    DESCRIPTION "The Diameter application which the result-code is referring to."
    ::= { homesteadCxSARResultsEntry 2 }

homesteadCxSARResultsResultCodeScope OBJECT-TYPE
    SYNTAX      Unsigned32 (0..6000)
    MAX-ACCESS  not-accessible
    STATUS      current
    DESCRIPTION "The result-code returned in the answer."
    ::= { homesteadCxSARResultsEntry 3 }

homesteadCxSARResultsCount OBJECT-TYPE
    SYNTAX      Unsigned32
    MAX-ACCESS  read-only
    STATUS      current
    DESCRIPTION "The number of times that result-code has been returned as an
                 answer over the time period."
    ::= { homesteadCxSARResultsEntry 4 }

homesteadCxUARResultsTable OBJECT-TYPE
    SYNTAX SEQUENCE OF HomesteadCxUARResultsEntry
    MAX-ACCESS not-accessible
    STATUS current
    DESCRIPTION "The number of UARs sent over the Cx interface indexed by
                 result-code"
    ::= { homestead 12 }

homesteadCxUARResultsEntry OBJECT-TYPE
    SYNTAX       HomesteadCxUARResultsEntry
    MAX-ACCESS   not-accessible
    STATUS       current
    DESCRIPTION  "The number of UARs sent over the Cx interface"
    INDEX        { homesteadCxUARResultsTimeScope,
                   homesteadCxUARResultsDiameterAppIdScope,
                   homesteadCxUARResultsResultCodeScope }
    ::= { homesteadCxUARResultsTable 1 }

HomesteadCxUARResultsEntry ::= SEQUENCE
{
  homesteadCxUARResultsTimeScope           INTEGER,
  homesteadCxUARResultsDiameterAppIdScope  INTEGER,
  homesteadCxUARResultsResultCodeScope     Unsigned32,
  homesteadCxUARResultsCount               Unsigned32
}

homesteadCxUARResultsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCxUARResultsEntry 1 }

homesteadCxUARResultsDiameterAppIdScope OBJECT-TYPE
    SYNTAX      INTEGER {
                  scopeBase(0),
                  scope3GPP(1),
                  scopeTimeout(2)
                }
    MAX-ACCESS  not-accessible
    STATUS      current
    DESCRIPTION "The Diameter application which the result-code is referring to."
    ::= { homesteadCxUARResultsEntry 2 }

homesteadCxUARResultsResultCodeScope OBJECT-TYPE
    SYNTAX      Unsigned32 (0..6000)
    MAX-ACCESS  not-accessible
    STATUS      current
    DESCRIPTION "The result-code returned in the answer."
    ::= { homesteadCxUARResultsEntry 3 }

homesteadCxUARResultsCount OBJECT-TYPE
    SYNTAX      Unsigned32
    MAX-ACCESS  read-only
    STATUS      current
    DESCRIPTION "The number of times that result-code has been returned as an
                 answer over the time period."
    ::= { homesteadCxUARResultsEntry 4 }

homesteadCxLIRResultsTable OBJECT-TYPE
    SYNTAX SEQUENCE OF HomesteadCxLIRResultsEntry
    MAX-ACCESS not-accessible
    STATUS current
    DESCRIPTION "The number of LIRs sent over the Cx interface indexed by
                 result-code"
    ::= { homestead 13 }

homesteadCxLIRResultsEntry OBJECT-TYPE
    SYNTAX       HomesteadCxLIRResultsEntry
    MAX-ACCESS   not-accessible
    STATUS       current
    DESCRIPTION  "The number of LIRs sent over the Cx interface"
    INDEX        { homesteadCxLIRResultsTimeScope,
                   homesteadCxLIRResultsDiameterAppIdScope,
                   homesteadCxLIRResultsResultCodeScope }
    ::= { homesteadCxLIRResultsTable 1 }

HomesteadCxLIRResultsEntry ::= SEQUENCE
{
  homesteadCxLIRResultsTimeScope           INTEGER,
  homesteadCxLIRResultsDiameterAppIdScope  INTEGER,
  homesteadCxLIRResultsResultCodeScope     Unsigned32,
  homesteadCxLIRResultsCount               Unsigned32
}

homesteadCxLIRResultsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCxLIRResultsEntry 1 }

homesteadCxLIRResultsDiameterAppIdScope OBJECT-TYPE
    SYNTAX      INTEGER {
                  scopeBase(0),
                  scope3GPP(1),
                  scopeTimeout(2)
                }
    MAX-ACCESS  not-accessible
    STATUS      current
    DESCRIPTION "The Diameter application which the result-code is referring to."
    ::= { homesteadCxLIRResultsEntry 2 }

homesteadCxLIRResultsResultCodeScope OBJECT-TYPE
    SYNTAX      Unsigned32 (0..6000)
    MAX-ACCESS  not-accessible
    STATUS      current
    DESCRIPTION "The result-code returned in the answer."
    ::= { homesteadCxLIRResultsEntry 3 }

homesteadCxLIRResultsCount OBJECT-TYPE
    SYNTAX      Unsigned32
    MAX-ACCESS  read-only
    STATUS      current
    DESCRIPTION "The number of times that result-code has been returned as an
                 answer over the time period."
    ::= { homesteadCxLIRResultsEntry 4 }

homesteadCxPPRResultsTable OBJECT-TYPE
    SYNTAX SEQUENCE OF HomesteadCxPPRResultsEntry
    MAX-ACCESS not-accessible
    STATUS current
    DESCRIPTION "The number of PPRs received over the Cx interface indexed by
                 result-code"
    ::= { homestead 14 }

homesteadCxPPRResultsEntry OBJECT-TYPE
    SYNTAX       HomesteadCxPPRResultsEntry
    MAX-ACCESS   not-accessible
    STATUS       current
    DESCRIPTION  "The number of PPRs received over the Cx interface"
    INDEX        { homesteadCxPPRResultsTimeScope,
                   homesteadCxPPRResultsDiameterAppIdScope,
                   homesteadCxPPRResultsResultCodeScope }
    ::= { homesteadCxPPRResultsTable 1 }

HomesteadCxPPRResultsEntry ::= SEQUENCE
{
  homesteadCxPPRResultsTimeScope           INTEGER,
  homesteadCxPPRResultsDiameterAppIdScope  INTEGER,
  homesteadCxPPRResultsResultCodeScope     Unsigned32,
  homesteadCxPPRResultsCount               Unsigned32
}

homesteadCxPPRResultsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCxPPRResultsEntry 1 }

homesteadCxPPRResultsDiameterAppIdScope OBJECT-TYPE
    SYNTAX      INTEGER {
                  scopeBase(0),
                  scope3GPP(1),
                  scopeTimeout(2)
                }
    MAX-ACCESS  not-accessible
    STATUS      current
    DESCRIPTION "The Diameter application which the result-code is referring to."
    ::= { homesteadCxPPRResultsEntry 2 }

homesteadCxPPRResultsResultCodeScope OBJECT-TYPE
    SYNTAX      Unsigned32 (0..6000)
    MAX-ACCESS  not-accessible
    STATUS      current
    DESCRIPTION "The result-code returned in the answer."
    ::= { homesteadCxPPRResultsEntry 3 }

homesteadCxPPRResultsCount OBJECT-TYPE
    SYNTAX      Unsigned32
    MAX-ACCESS  read-only
    STATUS      current
    DESCRIPTION "The number of times that result-code has been returned as an
                 answer over the time period."
    ::= { homesteadCxPPRResultsEntry 4 }

homesteadCxRTRResultsTable OBJECT-TYPE
    SYNTAX SEQUENCE OF HomesteadCxRTRResultsEntry
    MAX-ACCESS not-accessible
    STATUS current
    DESCRIPTION "The number of RTRs received over the Cx interface indexed by
                 result-code"
    ::= { homestead 15 }

homesteadCxRTRResultsEntry OBJECT-TYPE
    SYNTAX       HomesteadCxRTRResultsEntry
    MAX-ACCESS   not-accessible
    STATUS       current
    DESCRIPTION  "The number of RTRs received over the Cx interface"
    INDEX        { homesteadCxRTRResultsTimeScope,
                   homesteadCxRTRResultsDiameterAppIdScope,
                   homesteadCxRTRResultsResultCodeScope }
    ::= { homesteadCxRTRResultsTable 1 }

HomesteadCxRTRResultsEntry ::= SEQUENCE
{
  homesteadCxRTRResultsTimeScope           INTEGER,
  homesteadCxRTRResultsDiameterAppIdScope  INTEGER,
  homesteadCxRTRResultsResultCodeScope     Unsigned32,
  homesteadCxRTRResultsCount               Unsigned32
}

homesteadCxRTRResultsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { homesteadCxRTRResultsEntry 1 }

homesteadCxRTRResultsDiameterAppIdScope OBJECT-TYPE
    SYNTAX      INTEGER {
                  scopeBase(0),
                  scope3GPP(1),
                  scopeTimeout(2)
                }
    MAX-ACCESS  not-accessible
    STATUS      current
    DESCRIPTION "The Diameter application which the result-code is referring to."
    ::= { homesteadCxRTRResultsEntry 2 }

homesteadCxRTRResultsResultCodeScope OBJECT-TYPE
    SYNTAX      Unsigned32 (0..6000)
    MAX-ACCESS  not-accessible
    STATUS      current
    DESCRIPTION "The result-code returned in the answer."
    ::= { homesteadCxRTRResultsEntry 3 }

homesteadCxRTRResultsCount OBJECT-TYPE
    SYNTAX      Unsigned32
    MAX-ACCESS  read-only
    STATUS      current
    DESCRIPTION "The number of times that result-code has been returned as an
                 answer over the time period."
    ::= { homesteadCxRTRResultsEntry 4 }

homesteadGroup OBJECT-GROUP
    OBJECTS {
      homesteadLatencyAverage,
      homesteadLatencyVariance,
      homesteadLatencyHWM,
      homesteadLatencyLWM,
      homesteadLatencyCount,
      homesteadHSSLatencyAverage,
      homesteadHSSLatencyVariance,
      homesteadHSSLatencyHWM,
      homesteadHSSLatencyLWM,
      homesteadHSSLatencyCount,
      homesteadCacheLatencyAverage,
      homesteadCacheLatencyVariance,
      homesteadCacheLatencyHWM,
      homesteadCacheLatencyLWM,
      homesteadCacheLatencyCount,
      homesteadDigestLatencyAverage,
      homesteadDigestLatencyVariance,
      homesteadDigestLatencyHWM,
      homesteadDigestLatencyLWM,
      homesteadDigestLatencyCount,
      homesteadSubscriptionLatencyAverage,
      homesteadSubscriptionLatencyVariance,
      homesteadSubscriptionLatencyHWM,
      homesteadSubscriptionLatencyLWM,
      homesteadSubscriptionLatencyCount,
      homesteadIncomingRequestsCount,
      homesteadRejectedOverloadCount,
      homesteadDiameterInvalidRealmCount,
      homesteadDiameterInvalidHostCount,
      homesteadCxMARResultsCount,
      homesteadCxSARResultsCount,
      homesteadCxUARResultsCount,
      homesteadCxLIRResultsCount,
      homesteadCxPPRResultsCount,
      homesteadCxRTRResultsCount
    }
    STATUS      current
    DESCRIPTION "Statistics exposed by Homestead"
    ::= { commonClearwaterObjectGroups 4 }


-- Astaire Entries

astaireBucketsNeedingResync OBJECT-TYPE
    SYNTAX      Unsigned32
    MAX-ACCESS  read-only
    STATUS      current
    DESCRIPTION "Count of buckets needing to be synchronized for the current
                 resynchronization operation.  Set to 0 if there is no outstanding
                 resynchronization operation - in particular, if it has already
                 completed."
    ::= { astaire 1 }

astaireBucketsResynchronized OBJECT-TYPE
    SYNTAX      Unsigned32
    MAX-ACCESS  read-only
    STATUS      current
    DESCRIPTION "Number of buckets already resynchronized during the current
                 resynchronization operation.  Set to 0 if there is no outstanding
                 resynchronization operation - in particular, if it has already
                 completed."
    ::= { astaire 2 }

astaireEntriesResynchronized OBJECT-TYPE
    SYNTAX      Unsigned32
    MAX-ACCESS  read-only
    STATUS      current
    DESCRIPTION "Number of entries already resynchronized during the current
                 resynchronization operation.  Set to 0 if there is no outstanding
                 resynchronization operation - in particular, if it has already
                 completed."
    ::= { astaire 3 }

astaireDataResynchronized OBJECT-TYPE
    SYNTAX      Unsigned32
    MAX-ACCESS  read-only
    STATUS      current
    DESCRIPTION "Amout of data (in bytes) already resynchronized during the current
                 resynchronization operation.  Set to 0 if there is no outstanding
                 resynchronization operation - in particular, if it has already
                 completed."
    ::= { astaire 4 }

astaireBandwidthTable OBJECT-TYPE
    SYNTAX SEQUENCE OF AstaireBandwidthEntry
    MAX-ACCESS  not-accessible
    STATUS      current
    DESCRIPTION "Resynchronization bandwidth for the given period."
    ::= { astaire 5 }

astaireBandwidthEntry OBJECT-TYPE
    SYNTAX      AstaireBandwidthEntry
    MAX-ACCESS  not-accessible
    STATUS      current
    DESCRIPTION "Resynchronization bandwidth."
    INDEX       { astaireBandwidthScope }
    ::= { astaireBandwidthTable 1 }

AstaireBandwidthEntry ::= SEQUENCE
{
    astaireBandwidthScope          INTEGER,
    astaireBandwidth               Unsigned32
}

astaireBandwidthScope OBJECT-TYPE
    SYNTAX      INTEGER {
                  scopePrevious5SecondPeriod(1)
                }
    MAX-ACCESS  not-accessible
    STATUS      current
    DESCRIPTION "The period over which the statistics were collected."
    ::= { astaireBandwidthEntry 1 }

astaireBandwidth OBJECT-TYPE
    SYNTAX      Unsigned32
    MAX-ACCESS  read-only
    STATUS      current
    DESCRIPTION "Resynchronization bandwidth (bytes per second) over the period."
    ::= { astaireBandwidthEntry 2 }

astaireConnectionTable OBJECT-TYPE
    SYNTAX SEQUENCE OF AstaireConnectionEntry
    MAX-ACCESS  not-accessible
    STATUS      current
    DESCRIPTION "Resynchronization statistics on a per-connection basis."
    ::= { astaire 6 }

astaireConnectionEntry OBJECT-TYPE
    SYNTAX      AstaireConnectionEntry
    MAX-ACCESS  not-accessible
    STATUS      current
    DESCRIPTION "Resynchronization statistics for a specific connection.  Entries only
                 exist while the connection is established - once it terminates, the entry
                 is deleted."
    INDEX { astaireConnectionInetAddrType,
            astaireConnectionInetAddr,
            astaireConnectionInetPort      }
    ::= { astaireConnectionTable 1 }

AstaireConnectionEntry ::= SEQUENCE
{
  astaireConnectionInetAddrType           InetAddressType,
  astaireConnectionInetAddr               InetAddress,
  astaireConnectionInetPort               Unsigned32,
  astaireConnectionBucketsNeedingResync   Unsigned32,
  astaireConnectionBucketsResynchronized  Unsigned32
}

astaireConnectionInetAddrType OBJECT-TYPE
    SYNTAX      InetAddressType
    MAX-ACCESS  not-accessible
    STATUS      current
    DESCRIPTION "Inet address type of the connection peer"
    ::= { astaireConnectionEntry 1 }

astaireConnectionInetAddr OBJECT-TYPE
    SYNTAX      InetAddress (SIZE (1..16))
    MAX-ACCESS  not-accessible
    STATUS      current
    DESCRIPTION "Inet address of the connection peer"
    ::= { astaireConnectionEntry 2 }

astaireConnectionInetPort OBJECT-TYPE
    SYNTAX      Unsigned32
    MAX-ACCESS  not-accessible
    STATUS      current
    DESCRIPTION "Port of the connection peer"
    ::= { astaireConnectionEntry 3 }

astaireConnectionBucketsNeedingResync OBJECT-TYPE
    SYNTAX      Unsigned32
    MAX-ACCESS  read-only
    STATUS      current
    DESCRIPTION "Count of buckets needing to be synchronized over this
                 connection for the current resynchronization operation."
    ::= { astaireConnectionEntry 4 }

astaireConnectionBucketsResynchronized OBJECT-TYPE
    SYNTAX      Unsigned32
    MAX-ACCESS  read-only
    STATUS      current
    DESCRIPTION "Number of buckets already resynchronized over this connection
                 during the current resynchronization operation."
    ::= { astaireConnectionEntry 5 }

astaireConnectionBucketTable OBJECT-TYPE
    SYNTAX SEQUENCE OF AstaireConnectionBucketEntry
    MAX-ACCESS  not-accessible
    STATUS      current
    DESCRIPTION "Resynchronization statistics on a per-connection and
                 per-bucket basis."
    ::= { astaire 7 }

astaireConnectionBucketEntry OBJECT-TYPE
    SYNTAX      AstaireConnectionBucketEntry
    MAX-ACCESS  not-accessible
    STATUS      current
    DESCRIPTION "Resynchronization statistics for a specific connection and
                 bucket."
    INDEX { astaireConnectionBucketInetAddrType,
            astaireConnectionBucketInetAddr,
            astaireConnectionBucketInetPort,
            astaireConnectionBucketId }
    ::= { astaireConnectionBucketTable 1 }

AstaireConnectionBucketEntry ::= SEQUENCE
{
  astaireConnectionBucketInetAddrType           InetAddressType,
  astaireConnectionBucketInetAddr               InetAddress,
  astaireConnectionBucketInetPort               Unsigned32,
  astaireConnectionBucketId                     Unsigned32,
  astaireConnectionBucketEntriesResynchronized  Unsigned32,
  astaireConnectionBucketDataResynchronized     Unsigned32
}

astaireConnectionBucketInetAddrType OBJECT-TYPE
    SYNTAX      InetAddressType
    MAX-ACCESS  not-accessible
    STATUS      current
    DESCRIPTION "Inet address type of the connection peer"
    ::= { astaireConnectionBucketEntry 1 }

astaireConnectionBucketInetAddr OBJECT-TYPE
    SYNTAX      InetAddress (SIZE (1..16))
    MAX-ACCESS  not-accessible
    STATUS      current
    DESCRIPTION "Inet address of the connection peer"
    ::= { astaireConnectionBucketEntry 2 }

astaireConnectionBucketInetPort OBJECT-TYPE
    SYNTAX      Unsigned32
    MAX-ACCESS  not-accessible
    STATUS      current
    DESCRIPTION "Port of the connection peer"
    ::= { astaireConnectionBucketEntry 3 }

astaireConnectionBucketId OBJECT-TYPE
    SYNTAX      Unsigned32
    MAX-ACCESS  not-accessible
    STATUS      current
    DESCRIPTION "Identifier of this bucket."
    ::= { astaireConnectionBucketEntry 4 }

astaireConnectionBucketEntriesResynchronized OBJECT-TYPE
    SYNTAX      Unsigned32
    MAX-ACCESS  read-only
    STATUS      current
    DESCRIPTION "Number of entries already resynchronized during the current
                 resynchronization operation on this connection and bucket."
    ::= { astaireConnectionBucketEntry 5 }

astaireConnectionBucketDataResynchronized OBJECT-TYPE
    SYNTAX      Unsigned32
    MAX-ACCESS  read-only
    STATUS      current
    DESCRIPTION "Amout of data (in bytes) already resynchronized during the current
                 resynchronization operation on this connection and bucket."
    ::= { astaireConnectionBucketEntry 6 }

astaireConnectionBucketBandwidthTable OBJECT-TYPE
    SYNTAX SEQUENCE OF AstaireConnectionBucketBandwidthEntry
    MAX-ACCESS  not-accessible
    STATUS      current
    DESCRIPTION "Resynchronization bandwidth for this bucket for the given period."
    ::= { astaire 8 }

astaireConnectionBucketBandwidthEntry OBJECT-TYPE
    SYNTAX      AstaireConnectionBucketBandwidthEntry
    MAX-ACCESS  not-accessible
    STATUS      current
    DESCRIPTION "Resynchronization bandwidth for this bucket."
    INDEX { astaireConnectionBucketInetAddrType,
            astaireConnectionBucketInetAddr,
            astaireConnectionBucketInetPort,
            astaireConnectionBucketId,
            astaireConnectionBucketBandwidthScope }
    ::= { astaireConnectionBucketBandwidthTable 1 }

AstaireConnectionBucketBandwidthEntry ::= SEQUENCE
{
    astaireConnectionBucketBandwidthScope        INTEGER,
    astaireConnectionBucketBandwidth             Unsigned32
}

astaireConnectionBucketBandwidthScope OBJECT-TYPE
    SYNTAX      INTEGER {
                  scopePrevious5SecondPeriod(1)
                }
    MAX-ACCESS  not-accessible
    STATUS      current
    DESCRIPTION "The period over which the statistics were collected."
    ::= { astaireConnectionBucketBandwidthEntry 5 }

astaireConnectionBucketBandwidth OBJECT-TYPE
    SYNTAX      Unsigned32
    MAX-ACCESS  read-only
    STATUS      current
    DESCRIPTION "Resynchronization bandwidth (bytes per second) over the period."
    ::= { astaireConnectionBucketBandwidthEntry 6 }

astaireGroup OBJECT-GROUP
    OBJECTS {
        astaireBucketsNeedingResync,
        astaireBucketsResynchronized,
        astaireEntriesResynchronized,
        astaireDataResynchronized,
        astaireBandwidth,
        astaireConnectionBucketsNeedingResync,
        astaireConnectionBucketsResynchronized,
        astaireConnectionBucketEntriesResynchronized,
        astaireConnectionBucketDataResynchronized,
        astaireConnectionBucketBandwidth
    }
    STATUS      current
    DESCRIPTION "Statistics exposed by Astaire"
    ::= { commonClearwaterObjectGroups 8 }

-- Chronos Entries

chronosRemainingNodesQuery OBJECT-TYPE
    SYNTAX      Unsigned32
    MAX-ACCESS  read-only
    STATUS      current
    DESCRIPTION "Current count of the remaining Chronos nodes to query during a
                 scaling operation."
    ::= { chronos 1 }

chronosTimersProcessedTable OBJECT-TYPE
    SYNTAX SEQUENCE OF ChronosTimersProcessedEntry
    MAX-ACCESS not-accessible
    STATUS current
    DESCRIPTION "Total number of timers processed handled by this Chronos over
                 the given period."
    ::= { chronos 2 }

chronosTimersProcessedEntry OBJECT-TYPE
    SYNTAX      ChronosTimersProcessedEntry
    MAX-ACCESS  not-accessible
    STATUS      current
    DESCRIPTION "The total number of timers processed"
    INDEX       { chronosTimersProcessedScope }
    ::= { chronosTimersProcessedTable 1 }

ChronosTimersProcessedEntry ::= SEQUENCE
{
  chronosTimersProcessedScope          INTEGER,
  chronosTimersProcessedCount          Unsigned32
}

chronosTimersProcessedScope OBJECT-TYPE
    SYNTAX      INTEGER {
                  scopePrevious5SecondPeriod(1)
                }
    MAX-ACCESS  not-accessible
    STATUS      current
    DESCRIPTION "The period over which the statistics were collected."
    ::= { chronosTimersProcessedEntry 1 }

chronosTimersProcessedCount OBJECT-TYPE
    SYNTAX      Unsigned32
    MAX-ACCESS  read-only
    STATUS      current
    DESCRIPTION "The total number of timers processed over the period."
    ::= { chronosTimersProcessedEntry 2 }

chronosInvalidTimersProcessedTable OBJECT-TYPE
    SYNTAX SEQUENCE OF ChronosInvalidTimersProcessedEntry
    MAX-ACCESS not-accessible
    STATUS current
    DESCRIPTION "Total number of invalid timers processed by this Chronos over
                 the given period."
    ::= { chronos 3 }

chronosInvalidTimersProcessedEntry OBJECT-TYPE
    SYNTAX      ChronosInvalidTimersProcessedEntry
    MAX-ACCESS  not-accessible
    STATUS      current
    DESCRIPTION "The total number of invalid timers processed"
    INDEX       { chronosInvalidTimersProcessedScope }
    ::= { chronosInvalidTimersProcessedTable 1 }

ChronosInvalidTimersProcessedEntry ::= SEQUENCE
{
  chronosInvalidTimersProcessedScope          INTEGER,
  chronosInvalidTimersProcessedCount          Unsigned32
}

chronosInvalidTimersProcessedScope OBJECT-TYPE
    SYNTAX      INTEGER {
                  scopePrevious5SecondPeriod(1)
                }
    MAX-ACCESS  not-accessible
    STATUS      current
    DESCRIPTION "The period over which the statistics were collected."
    ::= { chronosInvalidTimersProcessedEntry 1 }

chronosInvalidTimersProcessedCount OBJECT-TYPE
    SYNTAX      Unsigned32
    MAX-ACCESS  read-only
    STATUS      current
    DESCRIPTION "The total number of invalid timers processed over the period."
    ::= { chronosInvalidTimersProcessedEntry 2 }

chronosAllTimersTable OBJECT-TYPE
    SYNTAX SEQUENCE OF ChronosAllTimersEntry
    MAX-ACCESS not-accessible
    STATUS current
    DESCRIPTION "Continuous accumulated counts of all
                 timers on this Chronos node, measured
                 and weighted over time scopes."
    ::= { chronos 4 }

chronosAllTimersEntry OBJECT-TYPE
    SYNTAX      ChronosAllTimersEntry
    MAX-ACCESS  not-accessible
    STATUS      current
    DESCRIPTION "The average, variance, LWM, HWM and
                 actions total of all timers on this
                 Chronos node, over time."
    INDEX       { chronosAllTimersScope }
    ::= { chronosAllTimersTable 1 }

ChronosAllTimersEntry ::= SEQUENCE
{
  chronosAllTimersScope       INTEGER,
  chronosAllTimersAverage     Unsigned32,
  chronosAllTimersVariance    Unsigned32,
  chronosAllTimersHWM         Unsigned32,
  chronosAllTimersLWM         Unsigned32,
  chronosAllTimersActions     Unsigned32
}

chronosAllTimersScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { chronosAllTimersEntry 1 }

chronosAllTimersAverage OBJECT-TYPE
    SYNTAX      Unsigned32
    MAX-ACCESS  read-only
    STATUS      current
    DESCRIPTION "The average number of timers active over the period."
    ::= { chronosAllTimersEntry 2 }

chronosAllTimersVariance OBJECT-TYPE
    SYNTAX      Unsigned32
    MAX-ACCESS  read-only
    STATUS      current
    DESCRIPTION "The variance of the number of timers over the period."
    ::= { chronosAllTimersEntry 3 }

chronosAllTimersHWM OBJECT-TYPE
    SYNTAX      Unsigned32
    MAX-ACCESS  read-only
    STATUS      current
    DESCRIPTION "The highest number of timers over the period."
    ::= { chronosAllTimersEntry 4 }

chronosAllTimersLWM OBJECT-TYPE
    SYNTAX      Unsigned32
    MAX-ACCESS  read-only
    STATUS      current
    DESCRIPTION "The lowest number of timers over the period."
    ::= { chronosAllTimersEntry 5 }

chronosAllTimersActions OBJECT-TYPE
    SYNTAX      Unsigned32
    MAX-ACCESS  read-only
    STATUS      current
    DESCRIPTION "The number of actions made over the period."
    ::= { chronosAllTimersEntry 6 }

chronosInstantaneousCounts OBJECT IDENTIFIER ::= { chronos 5 }

chronosCallInstantaneousCount OBJECT-TYPE
    SYNTAX      Unsigned32
    MAX-ACCESS  read-only
    STATUS      current
    DESCRIPTION "The instantaneous number of CALL
                 timers stored by this Chronos."
    ::= { chronosInstantaneousCounts 1 }

chronosSubInstantaneousCount OBJECT-TYPE
    SYNTAX      Unsigned32
    MAX-ACCESS  read-only
    STATUS      current
    DESCRIPTION "The instantaneous number of SUB
                 timers stored by this Chronos."
    ::= { chronosInstantaneousCounts 2 }

chronosBindInstantaneousCount OBJECT-TYPE
    SYNTAX      Unsigned32
    MAX-ACCESS  read-only
    STATUS      current
    DESCRIPTION "The instantaneous number of BIND
                 timers stored by this Chronos."
    ::= { chronosInstantaneousCounts 3 }

chronosRegInstantaneousCount OBJECT-TYPE
    SYNTAX      Unsigned32
    MAX-ACCESS  read-only
    STATUS      current
    DESCRIPTION "The instantaneous number of REG
                 timers stored by this Chronos."
    ::= { chronosInstantaneousCounts 4 }

chronosCallTable OBJECT-TYPE
    SYNTAX SEQUENCE OF ChronosCallEntry
    MAX-ACCESS         not-accessible
    STATUS             current
    DESCRIPTION        "The total number of CALL timers this Chronos node
                       is managing. This includes timers for which this node
                       is primary, and timers for which this node is a backup.
                       These statistics are only valid on Chronos nodes in the
                       Ralf cluster."
    ::= { chronos 6 }

chronosCallEntry OBJECT-TYPE
    SYNTAX      ChronosCallEntry
    MAX-ACCESS  not-accessible
    STATUS      current
    DESCRIPTION "The average, variance, HWM and LWM of
                 the CALL timers stored by this Chronos"
    INDEX       { chronosCallScope }
    ::= { chronosCallTable 1 }

ChronosCallEntry ::= SEQUENCE
{
  chronosCallScope        INTEGER,
  chronosCallAverage      Unsigned32,
  chronosCallVariance     Unsigned32,
  chronosCallHWM          Unsigned32,
  chronosCallLWM          Unsigned32
}

chronosCallScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { chronosCallEntry 1 }

chronosCallAverage OBJECT-TYPE
    SYNTAX      Unsigned32
    MAX-ACCESS  read-only
    STATUS      current
    DESCRIPTION "The average number of CALL timers
                 stored over the period."
    ::= { chronosCallEntry 2 }

chronosCallVariance OBJECT-TYPE
    SYNTAX      Unsigned32
    MAX-ACCESS  read-only
    STATUS      current
    DESCRIPTION "The variance of the CALL timers
                 stored over the period."
    ::= { chronosCallEntry 3 }

chronosCallHWM OBJECT-TYPE
    SYNTAX      Unsigned32
    MAX-ACCESS  read-only
    STATUS      current
    DESCRIPTION "The highest number of CALL timers stored
                 over the period."
    ::= { chronosCallEntry 4 }

chronosCallLWM OBJECT-TYPE
    SYNTAX      Unsigned32
    MAX-ACCESS  read-only
    STATUS      current
    DESCRIPTION "The lowest number of CALL timers stored
                 over the period."
    ::= { chronosCallEntry 5 }

chronosSubTable OBJECT-TYPE
    SYNTAX SEQUENCE OF ChronosSubEntry
    MAX-ACCESS         not-accessible
    STATUS             current
    DESCRIPTION        "The total number of SUB timers
                        this Chronos node is managing."
    ::= { chronos 7 }

chronosSubEntry OBJECT-TYPE
    SYNTAX      ChronosSubEntry
    MAX-ACCESS  not-accessible
    STATUS      current
    DESCRIPTION "The average, variance, HWM and LWM of
                 the SUB timers stored by this Chronos."
    INDEX       { chronosSubScope }
    ::= { chronosSubTable 1 }

ChronosSubEntry ::= SEQUENCE
{
  chronosSubScope        INTEGER,
  chronosSubAverage      Unsigned32,
  chronosSubVariance     Unsigned32,
  chronosSubHWM          Unsigned32,
  chronosSubLWM          Unsigned32
}

chronosSubScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { chronosSubEntry 1 }

chronosSubAverage OBJECT-TYPE
    SYNTAX      Unsigned32
    MAX-ACCESS  read-only
    STATUS      current
    DESCRIPTION "The average number of SUB timers
                 stored over the period."
    ::= { chronosSubEntry 2 }

chronosSubVariance OBJECT-TYPE
    SYNTAX      Unsigned32
    MAX-ACCESS  read-only
    STATUS      current
    DESCRIPTION "The variance of the SUB timers
                 stored over the period."
    ::= { chronosSubEntry 3 }

chronosSubHWM OBJECT-TYPE
    SYNTAX      Unsigned32
    MAX-ACCESS  read-only
    STATUS      current
    DESCRIPTION "The highest number of SUB timers stored
                 over the period."
    ::= { chronosSubEntry 4 }

chronosSubLWM OBJECT-TYPE
    SYNTAX      Unsigned32
    MAX-ACCESS  read-only
    STATUS      current
    DESCRIPTION "The lowest number of SUB timers stored
                 over the period."
    ::= { chronosSubEntry 5 }

chronosBindTable OBJECT-TYPE
    SYNTAX SEQUENCE OF ChronosBindEntry
    MAX-ACCESS         not-accessible
    STATUS             current
    DESCRIPTION        "The total number of BIND timers
                        this Chronos node is managing."
    ::= { chronos 8 }

chronosBindEntry OBJECT-TYPE
    SYNTAX      ChronosBindEntry
    MAX-ACCESS  not-accessible
    STATUS      current
    DESCRIPTION "The average, variance, HWM and LWM of
                 the Bind timers stored by this Chronos."
    INDEX       { chronosBindScope }
    ::= { chronosBindTable 1 }

ChronosBindEntry ::= SEQUENCE
{
  chronosBindScope        INTEGER,
  chronosBindAverage      Unsigned32,
  chronosBindVariance     Unsigned32,
  chronosBindHWM          Unsigned32,
  chronosBindLWM          Unsigned32
}

chronosBindScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { chronosBindEntry 1 }

chronosBindAverage OBJECT-TYPE
    SYNTAX      Unsigned32
    MAX-ACCESS  read-only
    STATUS      current
    DESCRIPTION "The average number of BIND timers
                 stored over the period."
    ::= { chronosBindEntry 2 }

chronosBindVariance OBJECT-TYPE
    SYNTAX      Unsigned32
    MAX-ACCESS  read-only
    STATUS      current
    DESCRIPTION "The variance of the BIND timers
                 stored over the period."
    ::= { chronosBindEntry 3 }

chronosBindHWM OBJECT-TYPE
    SYNTAX      Unsigned32
    MAX-ACCESS  read-only
    STATUS      current
    DESCRIPTION "The highest number of BIND timers stored
                 over the period."
    ::= { chronosBindEntry 4 }

chronosBindLWM OBJECT-TYPE
    SYNTAX      Unsigned32
    MAX-ACCESS  read-only
    STATUS      current
    DESCRIPTION "The lowest number of Bind timers stored
                 over the period."
    ::= { chronosBindEntry 5 }

chronosRegTable OBJECT-TYPE
    SYNTAX SEQUENCE OF ChronosRegEntry
    MAX-ACCESS         not-accessible
    STATUS             current
    DESCRIPTION        "The total number of REG timers this Chronos node
                       is managing. This includes REG timers for which this node
                       is primary, and timers for which this node is a backup.
                       These statistics are only valid on Chronos nodes in the
                       Sprout cluster."
    ::= { chronos 9 }

chronosRegEntry OBJECT-TYPE
    SYNTAX      ChronosRegEntry
    MAX-ACCESS  not-accessible
    STATUS      current
    DESCRIPTION "The average, variance, HWM and LWM of
                 the REG timers stored by this Chronos"
    INDEX       { chronosRegScope }
    ::= { chronosRegTable 1 }

ChronosRegEntry ::= SEQUENCE
{
  chronosRegScope        INTEGER,
  chronosRegAverage      Unsigned32,
  chronosRegVariance     Unsigned32,
  chronosRegHWM          Unsigned32,
  chronosRegLWM          Unsigned32
}

chronosRegScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { chronosRegEntry 1 }

chronosRegAverage OBJECT-TYPE
    SYNTAX      Unsigned32
    MAX-ACCESS  read-only
    STATUS      current
    DESCRIPTION "The average number of REG timers
                 stored over the period."
    ::= { chronosRegEntry 2 }

chronosRegVariance OBJECT-TYPE
    SYNTAX      Unsigned32
    MAX-ACCESS  read-only
    STATUS      current
    DESCRIPTION "The variance of REG timers
                 stored over the period."
    ::= { chronosRegEntry 3 }

chronosRegHWM OBJECT-TYPE
    SYNTAX      Unsigned32
    MAX-ACCESS  read-only
    STATUS      current
    DESCRIPTION "The highest number of REG timers stored
                 over the period."
    ::= { chronosRegEntry 4 }

chronosRegLWM OBJECT-TYPE
    SYNTAX      Unsigned32
    MAX-ACCESS  read-only
    STATUS      current
    DESCRIPTION "The lowest number of REG timers stored
                 over the period."
    ::= { chronosRegEntry 5 }

chronosGroup OBJECT-GROUP
    OBJECTS {
        chronosRemainingNodesQuery,
        chronosTimersProcessedCount,
        chronosInvalidTimersProcessedCount,
        chronosAllTimersAverage,
        chronosAllTimersVariance,
        chronosAllTimersHWM,
        chronosAllTimersLWM,
        chronosAllTimersActions,
        chronosCallInstantaneousCount,
        chronosSubInstantaneousCount,
        chronosBindInstantaneousCount,
        chronosRegInstantaneousCount,
        chronosCallAverage,
        chronosCallVariance,
        chronosCallHWM,
        chronosCallLWM,
        chronosSubAverage,
        chronosSubVariance,
        chronosSubHWM,
        chronosSubLWM,
        chronosBindAverage,
        chronosBindVariance,
        chronosBindHWM,
        chronosBindLWM,
        chronosRegAverage,
        chronosRegVariance,
        chronosRegHWM,
        chronosRegLWM
    }
    STATUS      current
    DESCRIPTION "Statistics exposed by Chronos"
    ::= { commonClearwaterObjectGroups 7 }

-- End of common Clearwater MIB entries

-- Project Clearwater-specific MIB entries
--
-- Project Clearwater Module Compliance

projectClearwaterConformance OBJECT IDENTIFIER ::= { projectClearwater 20 }
projectClearwaterCompliance MODULE-COMPLIANCE
    STATUS current
    DESCRIPTION "Compliance statement for Project Clearwater-specific
                 components."
    MODULE
    GROUP bonoGroup
    DESCRIPTION "The bonoGroup must be exposed by Bono nodes"
    GROUP sproutPCGroup
    DESCRIPTION "The sproutPCGroup must be exposed by Sprout nodes"
    GROUP callDiversionASGroup
    DESCRIPTION "The callDiversionASGroup must be exposed by Call Diversion AS nodes"
    GROUP mementoGroup
    DESCRIPTION "The mementoGroup must be exposed by Memento nodes"
    GROUP geminiGroup
    DESCRIPTION "The geminiGroup must be exposed by nodes running Gemini"
    ::= { projectClearwaterConformance 1 }
projectClearwaterObjectGroups OBJECT IDENTIFIER ::= { projectClearwater 21 }

-- Bono entries

bonoConnectedClients OBJECT-TYPE
    SYNTAX      Unsigned32
    MAX-ACCESS  read-only
    STATUS      current
    DESCRIPTION "Current count of connected upstream clients.

                 This is calculated by counting the allocated
                 flow records and thus:

                  * Only counts clients if they have attempted
                    to register (either successfully or not)
                  * Multiple clients muxed onto a single connection
                    (e.g. behind a PBX) will be counted as one
                    client."
    ::= { bono 1 }

bonoLatencyTable OBJECT-TYPE
    SYNTAX SEQUENCE OF BonoLatencyEntry
    MAX-ACCESS not-accessible
    STATUS current
    DESCRIPTION "Latency of SIP requests handled by this Bono
                 over the given period.  Latency measured in
                 microseconds"
    ::= { bono 2 }

bonoLatencyEntry OBJECT-TYPE
    SYNTAX      BonoLatencyEntry
    MAX-ACCESS  not-accessible
    STATUS      current
    DESCRIPTION "The average, variance, LWM and HWM of SIP message
                 latency"
    INDEX       { bonoLatencyTimeFrame,
                  bonoLatencyScope }
    ::= { bonoLatencyTable 1 }

BonoLatencyEntry ::= SEQUENCE
{
  bonoLatencyTimeFrame      INTEGER,
  bonoLatencyScope          OCTET STRING,
  bonoLatencyAverage        Unsigned32,
  bonoLatencyVariance       Unsigned32,
  bonoLatencyHWM            Unsigned32,
  bonoLatencyLWM            Unsigned32,
  bonoLatencyCount          Unsigned32
}

bonoLatencyTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoLatencyEntry 1 }

bonoLatencyScope OBJECT-TYPE
    SYNTAX      OCTET STRING (SIZE(1..64))
    MAX-ACCESS  not-accessible
    STATUS      current
    DESCRIPTION "Statistic scope - should always take the value: node."
    ::= { bonoLatencyEntry 2 }

bonoLatencyAverage OBJECT-TYPE
    SYNTAX      Unsigned32
    MAX-ACCESS  read-only
    STATUS      current
    DESCRIPTION "The average latency over the period."
    ::= { bonoLatencyEntry 3 }

bonoLatencyVariance OBJECT-TYPE
    SYNTAX      Unsigned32
    MAX-ACCESS  read-only
    STATUS      current
    DESCRIPTION "The variance of the latency over the period."
    ::= { bonoLatencyEntry 4 }

bonoLatencyHWM OBJECT-TYPE
    SYNTAX      Unsigned32
    MAX-ACCESS  read-only
    STATUS      current
    DESCRIPTION "The highest latency over the period."
    ::= { bonoLatencyEntry 5 }

bonoLatencyLWM OBJECT-TYPE
    SYNTAX      Unsigned32
    MAX-ACCESS  read-only
    STATUS      current
    DESCRIPTION "The lowest latency over the period."
    ::= { bonoLatencyEntry 6 }

bonoLatencyCount OBJECT-TYPE
    SYNTAX      Unsigned32
    MAX-ACCESS  read-only
    STATUS      current
    DESCRIPTION "The total requests over the period."
    ::= { bonoLatencyEntry 7 }

core OBJECT IDENTIFIER ::= { bono 3 }

bonoConnectedSproutsTable OBJECT-TYPE
    SYNTAX SEQUENCE OF BonoConnectedSproutsEntry
    MAX-ACCESS not-accessible
    STATUS current
    DESCRIPTION "Statistics for each connected upstream Sprout node"
    ::= { core 1 }

bonoConnectedSproutsEntry OBJECT-TYPE
    SYNTAX BonoConnectedSproutsEntry
    MAX-ACCESS not-accessible
    STATUS current
    DESCRIPTION "Statistics for a single connected upstream Sprout"
    INDEX { bonoSproutInetAddrType,
            bonoSproutInetAddr      }
    ::= { bonoConnectedSproutsTable 1 }

BonoConnectedSproutsEntry ::= SEQUENCE
{
  bonoSproutInetAddrType    InetAddressType,
  bonoSproutInetAddr        InetAddress,
  bonoSproutConnectionCount Unsigned32
}

bonoSproutInetAddrType OBJECT-TYPE
    SYNTAX      InetAddressType
    MAX-ACCESS  not-accessible
    STATUS      current
    DESCRIPTION "Inet address type of the upstream Sprout"
    ::= { bonoConnectedSproutsEntry 1 }

bonoSproutInetAddr OBJECT-TYPE
    SYNTAX      InetAddress (SIZE (1..16))
    MAX-ACCESS  not-accessible
    STATUS      current
    DESCRIPTION "Inet address of the upstream Sprout"
    ::= { bonoConnectedSproutsEntry 2 }

bonoSproutConnectionCount OBJECT-TYPE
    SYNTAX      Unsigned32
    MAX-ACCESS  read-only
    STATUS      current
    DESCRIPTION "Current count of TCP connections from Bono to the
                 Sprout node, may include connections in setting-
                 up state"
    ::= { bonoConnectedSproutsEntry 3 }

bonoIncomingRequestsTable OBJECT-TYPE
    SYNTAX SEQUENCE OF BonoIncomingRequestsEntry
    MAX-ACCESS not-accessible
    STATUS current
    DESCRIPTION "Total number of incoming requests handled by this Bono over
                 the given period."
    ::= { bono 4 }

bonoIncomingRequestsEntry OBJECT-TYPE
    SYNTAX      BonoIncomingRequestsEntry
    MAX-ACCESS  not-accessible
    STATUS      current
    DESCRIPTION "The total number of incoming requests"
    INDEX       { bonoIncomingRequestsTimeFrame,
                  bonoIncomingRequestsScope }
    ::= { bonoIncomingRequestsTable 1 }

BonoIncomingRequestsEntry ::= SEQUENCE
{
  bonoIncomingRequestsTimeFrame      INTEGER,
  bonoIncomingRequestsScope          OCTET STRING,
  bonoIncomingRequestsCount          Unsigned32
}

bonoIncomingRequestsTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoIncomingRequestsEntry 1 }

bonoIncomingRequestsScope OBJECT-TYPE
    SYNTAX      OCTET STRING (SIZE(1..64))
    MAX-ACCESS  not-accessible
    STATUS      current
    DESCRIPTION "Statistic scope - should always take the value: node."
    ::= { bonoIncomingRequestsEntry 2 }

bonoIncomingRequestsCount OBJECT-TYPE
    SYNTAX      Unsigned32
    MAX-ACCESS  read-only
    STATUS      current
    DESCRIPTION "The total number of incoming requests over the period."
    ::= { bonoIncomingRequestsEntry 3 }

bonoRejectedOverloadTable OBJECT-TYPE
    SYNTAX SEQUENCE OF BonoRejectedOverloadEntry
    MAX-ACCESS not-accessible
    STATUS current
    DESCRIPTION "Total number of requests rejected due to overload by
                 this Bono over the given period."
    ::= { bono 5 }

bonoRejectedOverloadEntry OBJECT-TYPE
    SYNTAX      BonoRejectedOverloadEntry
    MAX-ACCESS  not-accessible
    STATUS      current
    DESCRIPTION "The total number of requests rejected due to overload"
    INDEX       { bonoRejectedOverloadTimeFrame,
                  bonoRejectedOverloadScope }
    ::= { bonoRejectedOverloadTable 1 }

BonoRejectedOverloadEntry ::= SEQUENCE
{
  bonoRejectedOverloadTimeFrame      INTEGER,
  bonoRejectedOverloadScope          OCTET STRING,
  bonoRejectedOverloadCount          Unsigned32
}

bonoRejectedOverloadTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoRejectedOverloadEntry 1 }

bonoRejectedOverloadScope OBJECT-TYPE
    SYNTAX      OCTET STRING (SIZE(1..64))
    MAX-ACCESS  not-accessible
    STATUS      current
    DESCRIPTION "Statistic scope - should always take the value: node."
    ::= { bonoRejectedOverloadEntry 2 }

bonoRejectedOverloadCount OBJECT-TYPE
    SYNTAX      Unsigned32
    MAX-ACCESS  read-only
    STATUS      current
    DESCRIPTION "The total number of rejected requests due to overload over the
                 period."
    ::= { bonoRejectedOverloadEntry 3 }

bonoQueueSizeTable OBJECT-TYPE
    SYNTAX SEQUENCE OF BonoQueueSizeEntry
    MAX-ACCESS not-accessible
    STATUS current
    DESCRIPTION "Average request queue size for this Bono"
    ::= { bono 6 }

bonoQueueSizeEntry OBJECT-TYPE
    SYNTAX      BonoQueueSizeEntry
    MAX-ACCESS  not-accessible
    STATUS      current
    DESCRIPTION "The average, variance, LWM and HWM of request queue size"
    INDEX       { bonoQueueSizeTimeFrame,
                  bonoQueueSizeScope }
    ::= { bonoQueueSizeTable 1 }

BonoQueueSizeEntry ::= SEQUENCE
{
  bonoQueueSizeTimeFrame      INTEGER,
  bonoQueueSizeScope          OCTET STRING,
  bonoQueueSizeAverage        Unsigned32,
  bonoQueueSizeVariance       Unsigned32,
  bonoQueueSizeHWM            Unsigned32,
  bonoQueueSizeLWM            Unsigned32,
  bonoQueueSizeCount          Unsigned32
}

bonoQueueSizeTimeFrame OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { bonoQueueSizeEntry 1 }

bonoQueueSizeScope OBJECT-TYPE
    SYNTAX      OCTET STRING (SIZE(1..64))
    MAX-ACCESS  not-accessible
    STATUS      current
    DESCRIPTION "Statistic scope - should always take the value: node."
    ::= { bonoQueueSizeEntry 2 }

bonoQueueSizeAverage OBJECT-TYPE
    SYNTAX      Unsigned32
    MAX-ACCESS  read-only
    STATUS      current
    DESCRIPTION "The average request queue size over the period."
    ::= { bonoQueueSizeEntry 3 }

bonoQueueSizeVariance OBJECT-TYPE
    SYNTAX      Unsigned32
    MAX-ACCESS  read-only
    STATUS      current
    DESCRIPTION "The variance of the queue size over the period."
    ::= { bonoQueueSizeEntry 4 }

bonoQueueSizeHWM OBJECT-TYPE
    SYNTAX      Unsigned32
    MAX-ACCESS  read-only
    STATUS      current
    DESCRIPTION "The highest queue size over the period."
    ::= { bonoQueueSizeEntry 5 }

bonoQueueSizeLWM OBJECT-TYPE
    SYNTAX      Unsigned32
    MAX-ACCESS  read-only
    STATUS      current
    DESCRIPTION "The lowest queue size over the period."
    ::= { bonoQueueSizeEntry 6 }

bonoQueueSizeCount OBJECT-TYPE
    SYNTAX      Unsigned32
    MAX-ACCESS  read-only
    STATUS      current
    DESCRIPTION "The total requests over the period."
    ::= { bonoQueueSizeEntry 7 }

bonoGroup OBJECT-GROUP
    OBJECTS {
      bonoConnectedClients,
      bonoLatencyAverage,
      bonoLatencyVariance,
      bonoLatencyHWM,
      bonoLatencyLWM,
      bonoLatencyCount,
      bonoSproutConnectionCount,
      bonoIncomingRequestsCount,
      bonoRejectedOverloadCount,
      bonoQueueSizeAverage,
      bonoQueueSizeVariance,
      bonoQueueSizeHWM,
      bonoQueueSizeLWM,
      bonoQueueSizeCount
    }
    STATUS      current
    DESCRIPTION "Statistics exposed by Bono"
    ::= { projectClearwaterObjectGroups 1 }

-- Sprout PC-specific entries

xdm OBJECT IDENTIFIER ::= { sprout 2 }

sproutConnectedHomersTable OBJECT-TYPE
    SYNTAX SEQUENCE OF SproutConnectedHomersEntry
    MAX-ACCESS not-accessible
    STATUS current
    DESCRIPTION "Statistics for each connected upstream Homer node"
    ::= { xdm 1 }

sproutConnectedHomersEntry OBJECT-TYPE
    SYNTAX SproutConnectedHomersEntry
    MAX-ACCESS not-accessible
    STATUS current
    DESCRIPTION "Statistics for a single connected upstream Homer"
    INDEX { sproutHomerInetAddrType,
            sproutHomerInetAddr      }
    ::= { sproutConnectedHomersTable 1 }

SproutConnectedHomersEntry ::= SEQUENCE
{
  sproutHomerInetAddrType    InetAddressType,
  sproutHomerInetAddr        InetAddress,
  sproutHomerConnectionCount Unsigned32
}

sproutHomerInetAddrType OBJECT-TYPE
    SYNTAX      InetAddressType
    MAX-ACCESS  not-accessible
    STATUS      current
    DESCRIPTION "Inet address type of the upstream Homer"
    ::= { sproutConnectedHomersEntry 1 }

sproutHomerInetAddr OBJECT-TYPE
    SYNTAX      InetAddress (SIZE (1..16))
    MAX-ACCESS  not-accessible
    STATUS      current
    DESCRIPTION "Inet address of the upstream Homer"
    ::= { sproutConnectedHomersEntry 2 }

sproutHomerConnectionCount OBJECT-TYPE
    SYNTAX      Unsigned32
    MAX-ACCESS  read-only
    STATUS      current
    DESCRIPTION "Current count of TCP connections from Sprout to the
                 Homer node, may include connections in setting-
                 up state"
    ::= { sproutConnectedHomersEntry 3 }

sproutHomerLatencyTable OBJECT-TYPE
    SYNTAX SEQUENCE OF SproutHomerLatencyEntry
    MAX-ACCESS not-accessible
    STATUS current
    DESCRIPTION "Latency of Homer requests made by this Sprout
                 over the given period.  Latency measured in
                 microseconds"
    ::= { xdm 2 }

sproutHomerLatencyEntry OBJECT-TYPE
    SYNTAX      SproutHomerLatencyEntry
    MAX-ACCESS  not-accessible
    STATUS      current
    DESCRIPTION "The average, variance, LWM and HWM of SIP message
                 latency"
    INDEX       { sproutHomerLatencyScope }
    ::= { sproutHomerLatencyTable 1 }

SproutHomerLatencyEntry ::= SEQUENCE
{
  sproutHomerLatencyScope          INTEGER,
  sproutHomerLatencyAverage        Unsigned32,
  sproutHomerLatencyVariance       Unsigned32,
  sproutHomerLatencyHWM            Unsigned32,
  sproutHomerLatencyLWM            Unsigned32,
  sproutHomerLatencyCount          Unsigned32
}

sproutHomerLatencyScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutHomerLatencyEntry 1 }

sproutHomerLatencyAverage OBJECT-TYPE
    SYNTAX      Unsigned32
    MAX-ACCESS  read-only
    STATUS      current
    DESCRIPTION "The average latency over the period."
    ::= { sproutHomerLatencyEntry 2 }

sproutHomerLatencyVariance OBJECT-TYPE
    SYNTAX      Unsigned32
    MAX-ACCESS  read-only
    STATUS      current
    DESCRIPTION "The variance of the latency over the period."
    ::= { sproutHomerLatencyEntry 3 }

sproutHomerLatencyHWM OBJECT-TYPE
    SYNTAX      Unsigned32
    MAX-ACCESS  read-only
    STATUS      current
    DESCRIPTION "The highest latency over the period."
    ::= { sproutHomerLatencyEntry 4 }

sproutHomerLatencyLWM OBJECT-TYPE
    SYNTAX      Unsigned32
    MAX-ACCESS  read-only
    STATUS      current
    DESCRIPTION "The lowest latency over the period."
    ::= { sproutHomerLatencyEntry 5 }

sproutHomerLatencyCount OBJECT-TYPE
    SYNTAX      Unsigned32
    MAX-ACCESS  read-only
    STATUS      current
    DESCRIPTION "The total requests over the period."
    ::= { sproutHomerLatencyEntry 6 }

sproutBGCFIncomingSIPTransactionsTable OBJECT-TYPE
    SYNTAX SEQUENCE OF SproutBGCFIncomingSIPTransactionsEntry
    MAX-ACCESS not-accessible
    STATUS current
    DESCRIPTION "Counts the number of attempts, successes and failures
                 of incoming SIP transactions for the BGCF, and (for
                 convenience) provides the percentage of attempts that were
                 successful. Note that CANCEL transactions are not currently
                 tracked in this table."
    ::= { sprout 22 }

sproutBGCFIncomingSIPTransactionsEntry OBJECT-TYPE
    SYNTAX      SproutBGCFIncomingSIPTransactionsEntry
    MAX-ACCESS  not-accessible
    STATUS      current
    DESCRIPTION "The number of attempts, successes and failures for
                 incoming SIP transactions for the BGCF, and the percentage
                 of attempts that were successful."
    INDEX       { sproutBGCFIncomingSIPTransactionsTimeScope,
                  sproutBGCFIncomingSIPTransactionsRequestScope }
    ::= { sproutBGCFIncomingSIPTransactionsTable 1 }

SproutBGCFIncomingSIPTransactionsEntry ::= SEQUENCE
{
  sproutBGCFIncomingSIPTransactionsTimeScope      INTEGER,
  sproutBGCFIncomingSIPTransactionsRequestScope   INTEGER,
  sproutBGCFIncomingSIPTransactionsAttempts       Unsigned32,
  sproutBGCFIncomingSIPTransactionsSuccesses      Unsigned32,
  sproutBGCFIncomingSIPTransactionsFailures       Unsigned32,
  sproutBGCFIncomingSIPTransactionsSuccessPercent Unsigned32
}

sproutBGCFIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutBGCFIncomingSIPTransactionsEntry 1 }

sproutBGCFIncomingSIPTransactionsRequestScope OBJECT-TYPE
    SYNTAX      RequestType
    MAX-ACCESS  not-accessible
    STATUS      current
    DESCRIPTION "The method type of the incoming transaction."
    ::= { sproutBGCFIncomingSIPTransactionsEntry 2 }

sproutBGCFIncomingSIPTransactionsAttempts OBJECT-TYPE
    SYNTAX      Unsigned32
    MAX-ACCESS  read-only
    STATUS      current
    DESCRIPTION "The number of incoming SIP transactions over the time period."
    ::= { sproutBGCFIncomingSIPTransactionsEntry 3 }

sproutBGCFIncomingSIPTransactionsSuccesses OBJECT-TYPE
    SYNTAX      Unsigned32
    MAX-ACCESS  read-only
    STATUS      current
    DESCRIPTION "The number of successful incoming SIP transactions over the
                 time period."
    ::= { sproutBGCFIncomingSIPTransactionsEntry 4 }

sproutBGCFIncomingSIPTransactionsFailures OBJECT-TYPE
    SYNTAX      Unsigned32
    MAX-ACCESS  read-only
    STATUS      current
    DESCRIPTION "The number of failed incoming SIP transactions over the
                 time period. Note that 3xx responses are counted as
                 transaction failures."
    ::= { sproutBGCFIncomingSIPTransactionsEntry 5 }

sproutBGCFIncomingSIPTransactionsSuccessPercent OBJECT-TYPE
    SYNTAX      Unsigned32
    UNITS       "/ 10000 %"
    MAX-ACCESS  read-only
    STATUS      current
    DESCRIPTION "The percentage of incoming SIP transactions over the
                 period that were successful. Reported in units of ten
                 thousandths of a percentage point. When there are zero
                 attempts made, the value will be 1000000 to represent 100%."
    ::= { sproutBGCFIncomingSIPTransactionsEntry 6 }

sproutBGCFOutgoingSIPTransactionsTable OBJECT-TYPE
    SYNTAX SEQUENCE OF SproutBGCFOutgoingSIPTransactionsEntry
    MAX-ACCESS not-accessible
    STATUS current
    DESCRIPTION "Counts the number of attempts, successes and failures
                 of outgoing SIP transactions for the BGCF, and (for
                 convenience) provides the percentage of attempts that were
                 successful. Note that CANCEL transactions are not currently
                 tracked in this table."
    ::= { sprout 23 }

sproutBGCFOutgoingSIPTransactionsEntry OBJECT-TYPE
    SYNTAX      SproutBGCFOutgoingSIPTransactionsEntry
    MAX-ACCESS  not-accessible
    STATUS      current
    DESCRIPTION "The number of attempts, successes and failures for
                 outgoing SIP transactions for the BGCF, and the percentage
                 of attempts that were successful."
    INDEX       { sproutBGCFOutgoingSIPTransactionsTimeScope,
                  sproutBGCFOutgoingSIPTransactionsRequestScope }
    ::= { sproutBGCFOutgoingSIPTransactionsTable 1 }

SproutBGCFOutgoingSIPTransactionsEntry ::= SEQUENCE
{
  sproutBGCFOutgoingSIPTransactionsTimeScope      INTEGER,
  sproutBGCFOutgoingSIPTransactionsRequestScope   INTEGER,
  sproutBGCFOutgoingSIPTransactionsAttempts       Unsigned32,
  sproutBGCFOutgoingSIPTransactionsSuccesses      Unsigned32,
  sproutBGCFOutgoingSIPTransactionsFailures       Unsigned32,
  sproutBGCFOutgoingSIPTransactionsSuccessPercent Unsigned32
}

sproutBGCFOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutBGCFOutgoingSIPTransactionsEntry 1 }

sproutBGCFOutgoingSIPTransactionsRequestScope OBJECT-TYPE
    SYNTAX      RequestType
    MAX-ACCESS  not-accessible
    STATUS      current
    DESCRIPTION "The method type of the outgoing transaction."
    ::= { sproutBGCFOutgoingSIPTransactionsEntry 2 }

sproutBGCFOutgoingSIPTransactionsAttempts OBJECT-TYPE
    SYNTAX      Unsigned32
    MAX-ACCESS  read-only
    STATUS      current
    DESCRIPTION "The number of outgoing SIP transactions over the time period."
    ::= { sproutBGCFOutgoingSIPTransactionsEntry 3 }

sproutBGCFOutgoingSIPTransactionsSuccesses OBJECT-TYPE
    SYNTAX      Unsigned32
    MAX-ACCESS  read-only
    STATUS      current
    DESCRIPTION "The number of successful outgoing SIP transactions over the
                 time period."
    ::= { sproutBGCFOutgoingSIPTransactionsEntry 4 }

sproutBGCFOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { sproutBGCFOutgoingSIPTransactionsEntry 5 }

sproutBGCFOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { sproutBGCFOutgoingSIPTransactionsEntry 6 }

sproutMMTelIncomingSIPTransactionsTable OBJECT-TYPE
    SYNTAX SEQUENCE OF SproutMMTelIncomingSIPTransactionsEntry
    MAX-ACCESS not-accessible
    STATUS current
    DESCRIPTION "Counts the number of attempts, successes and failures
                 of incoming SIP transactions for the MMTel, and (for
                 convenience) provides the percentage of attempts that were
                 successful. Note that CANCEL transactions are not currently
                 tracked in this table."
    ::= { sprout 24 }

sproutMMTelIncomingSIPTransactionsEntry OBJECT-TYPE
    SYNTAX      SproutMMTelIncomingSIPTransactionsEntry
    MAX-ACCESS  not-accessible
    STATUS      current
    DESCRIPTION "The number of attempts, successes and failures for
                 incoming SIP transactions for the MMTel, and the percentage
                 of attempts that were successful."
    INDEX       { sproutMMTelIncomingSIPTransactionsTimeScope,
                  sproutMMTelIncomingSIPTransactionsRequestScope }
    ::= { sproutMMTelIncomingSIPTransactionsTable 1 }

SproutMMTelIncomingSIPTransactionsEntry ::= SEQUENCE
{
  sproutMMTelIncomingSIPTransactionsTimeScope      INTEGER,
  sproutMMTelIncomingSIPTransactionsRequestScope   INTEGER,
  sproutMMTelIncomingSIPTransactionsAttempts       Unsigned32,
  sproutMMTelIncomingSIPTransactionsSuccesses      Unsigned32,
  sproutMMTelIncomingSIPTransactionsFailures       Unsigned32,
  sproutMMTelIncomingSIPTransactionsSuccessPercent Unsigned32
}

sproutMMTelIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutMMTelIncomingSIPTransactionsEntry 1 }

sproutMMTelIncomingSIPTransactionsRequestScope OBJECT-TYPE
    SYNTAX      RequestType
    MAX-ACCESS  not-accessible
    STATUS      current
    DESCRIPTION "The method type of the incoming transaction."
    ::= { sproutMMTelIncomingSIPTransactionsEntry 2 }

sproutMMTelIncomingSIPTransactionsAttempts OBJECT-TYPE
    SYNTAX      Unsigned32
    MAX-ACCESS  read-only
    STATUS      current
    DESCRIPTION "The number of incoming SIP transactions over the time period."
    ::= { sproutMMTelIncomingSIPTransactionsEntry 3 }

sproutMMTelIncomingSIPTransactionsSuccesses OBJECT-TYPE
    SYNTAX      Unsigned32
    MAX-ACCESS  read-only
    STATUS      current
    DESCRIPTION "The number of successful incoming SIP transactions over the
                 time period."
    ::= { sproutMMTelIncomingSIPTransactionsEntry 4 }

sproutMMTelIncomingSIPTransactionsFailures OBJECT-TYPE
    SYNTAX      Unsigned32
    MAX-ACCESS  read-only
    STATUS      current
    DESCRIPTION "The number of failed incoming SIP transactions over the
                 time period. Note that 3xx responses are counted as
                 transaction failures."
    ::= { sproutMMTelIncomingSIPTransactionsEntry 5 }

sproutMMTelIncomingSIPTransactionsSuccessPercent OBJECT-TYPE
    SYNTAX      Unsigned32
    UNITS       "/ 10000 %"
    MAX-ACCESS  read-only
    STATUS      current
    DESCRIPTION "The percentage of incoming SIP transactions over the
                 period that were successful. Reported in units of ten
                 thousandths of a percentage point. When there are zero
                 attempts made, the value will be 1000000 to represent 100%."
    ::= { sproutMMTelIncomingSIPTransactionsEntry 6 }

sproutMMTelOutgoingSIPTransactionsTable OBJECT-TYPE
    SYNTAX SEQUENCE OF SproutMMTelOutgoingSIPTransactionsEntry
    MAX-ACCESS not-accessible
    STATUS current
    DESCRIPTION "Counts the number of attempts, successes and failures
                 of outgoing SIP transactions for the MMTel, and (for
                 convenience) provides the percentage of attempts that were
                 successful. Note that CANCEL transactions are not currently
                 tracked in this table."
    ::= { sprout 25 }

sproutMMTelOutgoingSIPTransactionsEntry OBJECT-TYPE
    SYNTAX      SproutMMTelOutgoingSIPTransactionsEntry
    MAX-ACCESS  not-accessible
    STATUS      current
    DESCRIPTION "The number of attempts, successes and failures for
                 outgoing SIP transactions for the MMTel, and the percentage
                 of attempts that were successful."
    INDEX       { sproutMMTelOutgoingSIPTransactionsTimeScope,
                  sproutMMTelOutgoingSIPTransactionsRequestScope }
    ::= { sproutMMTelOutgoingSIPTransactionsTable 1 }

SproutMMTelOutgoingSIPTransactionsEntry ::= SEQUENCE
{
  sproutMMTelOutgoingSIPTransactionsTimeScope      INTEGER,
  sproutMMTelOutgoingSIPTransactionsRequestScope   INTEGER,
  sproutMMTelOutgoingSIPTransactionsAttempts       Unsigned32,
  sproutMMTelOutgoingSIPTransactionsSuccesses      Unsigned32,
  sproutMMTelOutgoingSIPTransactionsFailures       Unsigned32,
  sproutMMTelOutgoingSIPTransactionsSuccessPercent Unsigned32
}

sproutMMTelOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { sproutMMTelOutgoingSIPTransactionsEntry 1 }

sproutMMTelOutgoingSIPTransactionsRequestScope OBJECT-TYPE
    SYNTAX      RequestType
    MAX-ACCESS  not-accessible
    STATUS      current
    DESCRIPTION "The method type of the outgoing transaction."
    ::= { sproutMMTelOutgoingSIPTransactionsEntry 2 }

sproutMMTelOutgoingSIPTransactionsAttempts OBJECT-TYPE
    SYNTAX      Unsigned32
    MAX-ACCESS  read-only
    STATUS      current
    DESCRIPTION "The number of outgoing SIP transactions over the time period."
    ::= { sproutMMTelOutgoingSIPTransactionsEntry 3 }

sproutMMTelOutgoingSIPTransactionsSuccesses OBJECT-TYPE
    SYNTAX      Unsigned32
    MAX-ACCESS  read-only
    STATUS      current
    DESCRIPTION "The number of successful outgoing SIP transactions over the
                 time period."
    ::= { sproutMMTelOutgoingSIPTransactionsEntry 4 }

sproutMMTelOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { sproutMMTelOutgoingSIPTransactionsEntry 5 }

sproutMMTelOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { sproutMMTelOutgoingSIPTransactionsEntry 6 }

sproutPCGroup OBJECT-GROUP
    OBJECTS {
      sproutHomerConnectionCount,
      sproutHomerLatencyAverage,
      sproutHomerLatencyVariance,
      sproutHomerLatencyHWM,
      sproutHomerLatencyLWM,
      sproutHomerLatencyCount,
      sproutBGCFIncomingSIPTransactionsAttempts,
      sproutBGCFIncomingSIPTransactionsSuccesses,
      sproutBGCFIncomingSIPTransactionsFailures,
      sproutBGCFIncomingSIPTransactionsSuccessPercent,
      sproutBGCFOutgoingSIPTransactionsAttempts,
      sproutBGCFOutgoingSIPTransactionsSuccesses,
      sproutBGCFOutgoingSIPTransactionsFailures,
      sproutBGCFOutgoingSIPTransactionsSuccessPercent,
      sproutMMTelIncomingSIPTransactionsAttempts,
      sproutMMTelIncomingSIPTransactionsSuccesses,
      sproutMMTelIncomingSIPTransactionsFailures,
      sproutMMTelIncomingSIPTransactionsSuccessPercent,
      sproutMMTelOutgoingSIPTransactionsAttempts,
      sproutMMTelOutgoingSIPTransactionsSuccesses,
      sproutMMTelOutgoingSIPTransactionsFailures,
      sproutMMTelOutgoingSIPTransactionsSuccessPercent
    }
    STATUS      current
    DESCRIPTION "Project Clearwater-specific statistics exposed by Sprout"
    ::= { projectClearwaterObjectGroups 3 }

-- Call Diversion AS Entries

cdivAsDiversionsTable OBJECT-TYPE
    SYNTAX SEQUENCE OF CdivAsDiversionsEntry
    MAX-ACCESS not-accessible
    STATUS current
    DESCRIPTION "Counts of diversion reasons by the Call Diversion AS over
                 the given period."
    ::= { callDiversionAs 1 }

cdivAsDiversionsEntry OBJECT-TYPE
    SYNTAX      CdivAsDiversionsEntry
    MAX-ACCESS  not-accessible
    STATUS      current
    DESCRIPTION "Counts of diversion reasons by the Call Diversion AS"
    INDEX       { cdivAsDiversionsScope }
    ::= { cdivAsDiversionsTable 1 }

CdivAsDiversionsEntry ::= SEQUENCE
{
  cdivAsDiversionsScope          INTEGER,
  cdivAsTotal                    Unsigned32,
  cdivAsUnconditional            Unsigned32,
  cdivAsBusy                     Unsigned32,
  cdivAsNotRegistered            Unsigned32,
  cdivAsNoAnswer                 Unsigned32,
  cdivAsNotReachable             Unsigned32
}

cdivAsDiversionsScope OBJECT-TYPE
    SYNTAX      INTEGER {
                  scopePrevious5SecondPeriod(1)
                }
    MAX-ACCESS  not-accessible
    STATUS      current
    DESCRIPTION "The period over which the statistics were collected."
    ::= { cdivAsDiversionsEntry 1 }

cdivAsTotal OBJECT-TYPE
    SYNTAX      Unsigned32
    MAX-ACCESS  read-only
    STATUS      current
    DESCRIPTION "The total number of requests that were diverted."
    ::= { cdivAsDiversionsEntry 2 }

cdivAsUnconditional OBJECT-TYPE
    SYNTAX      Unsigned32
    MAX-ACCESS  read-only
    STATUS      current
    DESCRIPTION "The number of requests that were unconditionally diverted."
    ::= { cdivAsDiversionsEntry 3 }

cdivAsBusy OBJECT-TYPE
    SYNTAX      Unsigned32
    MAX-ACCESS  read-only
    STATUS      current
    DESCRIPTION "The number of requests that were diverted due to a busy
                 condition."
    ::= { cdivAsDiversionsEntry 4 }

cdivAsNotRegistered OBJECT-TYPE
    SYNTAX      Unsigned32
    MAX-ACCESS  read-only
    STATUS      current
    DESCRIPTION "The number of requests that were diverted due to a not
                 registered condition."
    ::= { cdivAsDiversionsEntry 5 }

cdivAsNoAnswer OBJECT-TYPE
    SYNTAX      Unsigned32
    MAX-ACCESS  read-only
    STATUS      current
    DESCRIPTION "The number of requests that were diverted due to a no answer
                 condition."
    ::= { cdivAsDiversionsEntry 6 }

cdivAsNotReachable OBJECT-TYPE
    SYNTAX      Unsigned32
    MAX-ACCESS  read-only
    STATUS      current
    DESCRIPTION "The number of requests that were diverted due to a not
                 reachable condition."
    ::= { cdivAsDiversionsEntry 7 }

cdivAsIncomingSIPTransactionsTable OBJECT-TYPE
    SYNTAX SEQUENCE OF CdivAsIncomingSIPTransactionsEntry
    MAX-ACCESS not-accessible
    STATUS current
    DESCRIPTION "Counts the number of attempts, successes and failures
                 of incoming SIP transactions for the Call Diversion AS, and
                 (for convenience) provides the percentage of attempts that were
                 successful. Note that CANCEL transactions are not currently
                 tracked in this table."
    ::= { callDiversionAs 2 }

cdivAsIncomingSIPTransactionsEntry OBJECT-TYPE
    SYNTAX      CdivAsIncomingSIPTransactionsEntry
    MAX-ACCESS  not-accessible
    STATUS      current
    DESCRIPTION "The number of attempts, successes and failures for
                 incoming SIP transactions for the Call Diversion AS, and the
                 percentage of attempts that were successful."
    INDEX       { cdivAsIncomingSIPTransactionsTimeScope,
                  cdivAsIncomingSIPTransactionsRequestScope }
    ::= { cdivAsIncomingSIPTransactionsTable 1 }

CdivAsIncomingSIPTransactionsEntry ::= SEQUENCE
{
  cdivAsIncomingSIPTransactionsTimeScope      INTEGER,
  cdivAsIncomingSIPTransactionsRequestScope   INTEGER,
  cdivAsIncomingSIPTransactionsAttempts       Unsigned32,
  cdivAsIncomingSIPTransactionsSuccesses      Unsigned32,
  cdivAsIncomingSIPTransactionsFailures       Unsigned32,
  cdivAsIncomingSIPTransactionsSuccessPercent Unsigned32
}

cdivAsIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { cdivAsIncomingSIPTransactionsEntry 1 }

cdivAsIncomingSIPTransactionsRequestScope OBJECT-TYPE
    SYNTAX      RequestType
    MAX-ACCESS  not-accessible
    STATUS      current
    DESCRIPTION "The method type of the incoming transaction."
    ::= { cdivAsIncomingSIPTransactionsEntry 2 }

cdivAsIncomingSIPTransactionsAttempts OBJECT-TYPE
    SYNTAX      Unsigned32
    MAX-ACCESS  read-only
    STATUS      current
    DESCRIPTION "The number of incoming SIP transactions over the time period."
    ::= { cdivAsIncomingSIPTransactionsEntry 3 }

cdivAsIncomingSIPTransactionsSuccesses OBJECT-TYPE
    SYNTAX      Unsigned32
    MAX-ACCESS  read-only
    STATUS      current
    DESCRIPTION "The number of successful incoming SIP transactions over the
                 time period."
    ::= { cdivAsIncomingSIPTransactionsEntry 4 }

cdivAsIncomingSIPTransactionsFailures OBJECT-TYPE
    SYNTAX      Unsigned32
    MAX-ACCESS  read-only
    STATUS      current
    DESCRIPTION "The number of failed incoming SIP transactions over the
                 time period. Note that 3xx responses are counted as
                 transaction failures."
    ::= { cdivAsIncomingSIPTransactionsEntry 5 }

cdivAsIncomingSIPTransactionsSuccessPercent OBJECT-TYPE
    SYNTAX      Unsigned32
    UNITS       "/ 10000 %"
    MAX-ACCESS  read-only
    STATUS      current
    DESCRIPTION "The percentage of incoming SIP transactions over the
                 period that were successful. Reported in units of ten
                 thousandths of a percentage point. When there are zero
                 attempts made, the value will be 1000000 to represent 100%."
    ::= { cdivAsIncomingSIPTransactionsEntry 6 }

cdivAsOutgoingSIPTransactionsTable OBJECT-TYPE
    SYNTAX SEQUENCE OF CdivAsOutgoingSIPTransactionsEntry
    MAX-ACCESS not-accessible
    STATUS current
    DESCRIPTION "Counts the number of attempts, successes and failures
                 of outgoing SIP transactions for the Call Diversion AS, and
                 (for convenience) provides the percentage of attempts that were
                 successful. Note that CANCEL transactions are not currently
                 tracked in this table."
    ::= { callDiversionAs 3 }

cdivAsOutgoingSIPTransactionsEntry OBJECT-TYPE
    SYNTAX      CdivAsOutgoingSIPTransactionsEntry
    MAX-ACCESS  not-accessible
    STATUS      current
    DESCRIPTION "The number of attempts, successes and failures for
                 outgoing SIP transactions for the Call Diversion AS, and the
                 percentage of attempts that were successful."
    INDEX       { cdivAsOutgoingSIPTransactionsTimeScope,
                  cdivAsOutgoingSIPTransactionsRequestScope }
    ::= { cdivAsOutgoingSIPTransactionsTable 1 }

CdivAsOutgoingSIPTransactionsEntry ::= SEQUENCE
{
  cdivAsOutgoingSIPTransactionsTimeScope      INTEGER,
  cdivAsOutgoingSIPTransactionsRequestScope   INTEGER,
  cdivAsOutgoingSIPTransactionsAttempts       Unsigned32,
  cdivAsOutgoingSIPTransactionsSuccesses      Unsigned32,
  cdivAsOutgoingSIPTransactionsFailures       Unsigned32,
  cdivAsOutgoingSIPTransactionsSuccessPercent Unsigned32
}

cdivAsOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { cdivAsOutgoingSIPTransactionsEntry 1 }

cdivAsOutgoingSIPTransactionsRequestScope OBJECT-TYPE
    SYNTAX      RequestType
    MAX-ACCESS  not-accessible
    STATUS      current
    DESCRIPTION "The method type of the outgoing transaction."
    ::= { cdivAsOutgoingSIPTransactionsEntry 2 }

cdivAsOutgoingSIPTransactionsAttempts OBJECT-TYPE
    SYNTAX      Unsigned32
    MAX-ACCESS  read-only
    STATUS      current
    DESCRIPTION "The number of outgoing SIP transactions over the time period."
    ::= { cdivAsOutgoingSIPTransactionsEntry 3 }

cdivAsOutgoingSIPTransactionsSuccesses OBJECT-TYPE
    SYNTAX      Unsigned32
    MAX-ACCESS  read-only
    STATUS      current
    DESCRIPTION "The number of successful outgoing SIP transactions over the
                 time period."
    ::= { cdivAsOutgoingSIPTransactionsEntry 4 }

cdivAsOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { cdivAsOutgoingSIPTransactionsEntry 5 }

cdivAsOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { cdivAsOutgoingSIPTransactionsEntry 6 }

callDiversionASGroup OBJECT-GROUP
    OBJECTS {
      cdivAsTotal,
      cdivAsUnconditional,
      cdivAsBusy,
      cdivAsNotRegistered,
      cdivAsNoAnswer,
      cdivAsNotReachable,
      cdivAsIncomingSIPTransactionsAttempts,
      cdivAsIncomingSIPTransactionsSuccesses,
      cdivAsIncomingSIPTransactionsFailures,
      cdivAsIncomingSIPTransactionsSuccessPercent,
      cdivAsOutgoingSIPTransactionsAttempts,
      cdivAsOutgoingSIPTransactionsSuccesses,
      cdivAsOutgoingSIPTransactionsFailures,
      cdivAsOutgoingSIPTransactionsSuccessPercent
    }
    STATUS      current
    DESCRIPTION "Statistics exposed by Call Diversion AS"
    ::= { projectClearwaterObjectGroups 6 }

-- Memento Entries

mementoSIP OBJECT IDENTIFIER ::= { memento 1 }

mementoCallsRecordedTable OBJECT-TYPE
    SYNTAX SEQUENCE OF MementoCallsRecordedEntry
    MAX-ACCESS  not-accessible
    STATUS      current
    DESCRIPTION "Counts of call record creation outcomes for the given period."
    ::= { mementoSIP 1 }

mementoCallsRecordedEntry OBJECT-TYPE
    SYNTAX      MementoCallsRecordedEntry
    MAX-ACCESS  not-accessible
    STATUS      current
    DESCRIPTION "Counts of call record creation outcomes"
    INDEX       { mementoCallsRecordedScope }
    ::= { mementoCallsRecordedTable 1 }

MementoCallsRecordedEntry ::= SEQUENCE
{
    mementoCallsRecordedScope            INTEGER,
    mementoCompletedCallsRecorded        Unsigned32,
    mementoFailedCallsRecorded           Unsigned32,
    mementoCallsNotRecordedDueToOverload Unsigned32
}

mementoCallsRecordedScope OBJECT-TYPE
    SYNTAX      INTEGER {
                  scopePrevious5SecondPeriod(1)
                }
    MAX-ACCESS  not-accessible
    STATUS      current
    DESCRIPTION "The period over which the statistics were collected."
    ::= { mementoCallsRecordedEntry 1 }

mementoCompletedCallsRecorded OBJECT-TYPE
    SYNTAX      Unsigned32
    MAX-ACCESS  read-only
    STATUS      current
    DESCRIPTION "The total number of successful calls recorded."
    ::= { mementoCallsRecordedEntry 2 }

mementoFailedCallsRecorded OBJECT-TYPE
    SYNTAX      Unsigned32
    MAX-ACCESS  read-only
    STATUS      current
    DESCRIPTION "The total number of failed call attempts recorded."
    ::= { mementoCallsRecordedEntry 3 }

mementoCallsNotRecordedDueToOverload OBJECT-TYPE
    SYNTAX      Unsigned32
    MAX-ACCESS  read-only
    STATUS      current
    DESCRIPTION "The total number of call records dropped due to overload."
    ::= { mementoCallsRecordedEntry 4 }

mementoSIPCassandraReadLatencyTable OBJECT-TYPE
    SYNTAX SEQUENCE OF MementoSIPCassandraReadLatencyEntry
    MAX-ACCESS not-accessible
    STATUS current
    DESCRIPTION "The average, variance, LWM and HWM of Cassandra database read
                 latency reported by the SIP AS component  Latency measured in
                 microseconds"
    ::= { mementoSIP 2 }

mementoSIPCassandraReadLatencyEntry OBJECT-TYPE
    SYNTAX      MementoSIPCassandraReadLatencyEntry
    MAX-ACCESS  not-accessible
    STATUS      current
    DESCRIPTION "The average, variance, LWM and HWM of Cassandra database read
                 latency reported by the SIP AS component"
    INDEX       { mementoSIPCassandraReadLatencyScope }
    ::= { mementoSIPCassandraReadLatencyTable 1 }

MementoSIPCassandraReadLatencyEntry ::= SEQUENCE
{
  mementoSIPCassandraReadLatencyScope          INTEGER,
  mementoSIPCassandraReadLatencyAverage        Unsigned32,
  mementoSIPCassandraReadLatencyVariance       Unsigned32,
  mementoSIPCassandraReadLatencyHWM            Unsigned32,
  mementoSIPCassandraReadLatencyLWM            Unsigned32,
  mementoSIPCassandraReadLatencyCount          Unsigned32
}

mementoSIPCassandraReadLatencyScope OBJECT-TYPE
    SYNTAX      INTEGER {
                  scopePrevious5SecondPeriod(1)
                }
    MAX-ACCESS  not-accessible
    STATUS      current
    DESCRIPTION "The period over which the statistics were collected."
    ::= { mementoSIPCassandraReadLatencyEntry 1 }

mementoSIPCassandraReadLatencyAverage OBJECT-TYPE
    SYNTAX      Unsigned32
    MAX-ACCESS  read-only
    STATUS      current
    DESCRIPTION "The average latency over the period."
    ::= { mementoSIPCassandraReadLatencyEntry 2 }

mementoSIPCassandraReadLatencyVariance OBJECT-TYPE
    SYNTAX      Unsigned32
    MAX-ACCESS  read-only
    STATUS      current
    DESCRIPTION "The variance of the latency over the period."
    ::= { mementoSIPCassandraReadLatencyEntry 3 }

mementoSIPCassandraReadLatencyHWM OBJECT-TYPE
    SYNTAX      Unsigned32
    MAX-ACCESS  read-only
    STATUS      current
    DESCRIPTION "The highest latency over the period."
    ::= { mementoSIPCassandraReadLatencyEntry 4 }

mementoSIPCassandraReadLatencyLWM OBJECT-TYPE
    SYNTAX      Unsigned32
    MAX-ACCESS  read-only
    STATUS      current
    DESCRIPTION "The lowest latency over the period."
    ::= { mementoSIPCassandraReadLatencyEntry 5 }

mementoSIPCassandraReadLatencyCount OBJECT-TYPE
    SYNTAX      Unsigned32
    MAX-ACCESS  read-only
    STATUS      current
    DESCRIPTION "The total number of reads over the period."
    ::= { mementoSIPCassandraReadLatencyEntry 6 }

mementoSIPCassandraWriteLatencyTable OBJECT-TYPE
    SYNTAX SEQUENCE OF MementoSIPCassandraWriteLatencyEntry
    MAX-ACCESS not-accessible
    STATUS current
    DESCRIPTION "The average, variance, LWM and HWM of Cassandra database write
                 latency reported by the SIP AS component.  Latency measured in
                 microseconds"
    ::= { mementoSIP 3 }

mementoSIPCassandraWriteLatencyEntry OBJECT-TYPE
    SYNTAX      MementoSIPCassandraWriteLatencyEntry
    MAX-ACCESS  not-accessible
    STATUS      current
    DESCRIPTION "The average, variance, LWM and HWM of Cassandra database write
                 latency reported by the SIP AS component."
    INDEX       { mementoSIPCassandraWriteLatencyScope }
    ::= { mementoSIPCassandraWriteLatencyTable 1 }

MementoSIPCassandraWriteLatencyEntry ::= SEQUENCE
{
  mementoSIPCassandraWriteLatencyScope          INTEGER,
  mementoSIPCassandraWriteLatencyAverage        Unsigned32,
  mementoSIPCassandraWriteLatencyVariance       Unsigned32,
  mementoSIPCassandraWriteLatencyHWM            Unsigned32,
  mementoSIPCassandraWriteLatencyLWM            Unsigned32,
  mementoSIPCassandraWriteLatencyCount          Unsigned32
}

mementoSIPCassandraWriteLatencyScope OBJECT-TYPE
    SYNTAX      INTEGER {
                  scopePrevious5SecondPeriod(1)
                }
    MAX-ACCESS  not-accessible
    STATUS      current
    DESCRIPTION "The period over which the statistics were collected."
    ::= { mementoSIPCassandraWriteLatencyEntry 1 }

mementoSIPCassandraWriteLatencyAverage OBJECT-TYPE
    SYNTAX      Unsigned32
    MAX-ACCESS  read-only
    STATUS      current
    DESCRIPTION "The average latency over the period."
    ::= { mementoSIPCassandraWriteLatencyEntry 2 }

mementoSIPCassandraWriteLatencyVariance OBJECT-TYPE
    SYNTAX      Unsigned32
    MAX-ACCESS  read-only
    STATUS      current
    DESCRIPTION "The variance of the latency over the period."
    ::= { mementoSIPCassandraWriteLatencyEntry 3 }

mementoSIPCassandraWriteLatencyHWM OBJECT-TYPE
    SYNTAX      Unsigned32
    MAX-ACCESS  read-only
    STATUS      current
    DESCRIPTION "The highest latency over the period."
    ::= { mementoSIPCassandraWriteLatencyEntry 4 }

mementoSIPCassandraWriteLatencyLWM OBJECT-TYPE
    SYNTAX      Unsigned32
    MAX-ACCESS  read-only
    STATUS      current
    DESCRIPTION "The lowest latency over the period."
    ::= { mementoSIPCassandraWriteLatencyEntry 5 }

mementoSIPCassandraWriteLatencyCount OBJECT-TYPE
    SYNTAX      Unsigned32
    MAX-ACCESS  read-only
    STATUS      current
    DESCRIPTION "The total number of writes over the period."
    ::= { mementoSIPCassandraWriteLatencyEntry 6 }

mementoIncomingSIPTransactionsTable OBJECT-TYPE
    SYNTAX SEQUENCE OF MementoIncomingSIPTransactionsEntry
    MAX-ACCESS not-accessible
    STATUS current
    DESCRIPTION "Counts the number of attempts, successes and failures
                 of incoming SIP transactions for Memento, and (for
                 convenience) provides the percentage of attempts that were
                 successful. Note that CANCEL transactions are not currently
                 tracked in this table."
    ::= { mementoSIP 4 }

mementoIncomingSIPTransactionsEntry OBJECT-TYPE
    SYNTAX      MementoIncomingSIPTransactionsEntry
    MAX-ACCESS  not-accessible
    STATUS      current
    DESCRIPTION "The number of attempts, successes and failures for
                 incoming SIP transactions for Memento, and the percentage
                 of attempts that were successful."
    INDEX       { mementoIncomingSIPTransactionsTimeScope,
                  mementoIncomingSIPTransactionsRequestScope }
    ::= { mementoIncomingSIPTransactionsTable 1 }

MementoIncomingSIPTransactionsEntry ::= SEQUENCE
{
  mementoIncomingSIPTransactionsTimeScope      INTEGER,
  mementoIncomingSIPTransactionsRequestScope   INTEGER,
  mementoIncomingSIPTransactionsAttempts       Unsigned32,
  mementoIncomingSIPTransactionsSuccesses      Unsigned32,
  mementoIncomingSIPTransactionsFailures       Unsigned32,
  mementoIncomingSIPTransactionsSuccessPercent Unsigned32
}

mementoIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { mementoIncomingSIPTransactionsEntry 1 }

mementoIncomingSIPTransactionsRequestScope OBJECT-TYPE
    SYNTAX      RequestType
    MAX-ACCESS  not-accessible
    STATUS      current
    DESCRIPTION "The method type of the incoming transaction."
    ::= { mementoIncomingSIPTransactionsEntry 2 }

mementoIncomingSIPTransactionsAttempts OBJECT-TYPE
    SYNTAX      Unsigned32
    MAX-ACCESS  read-only
    STATUS      current
    DESCRIPTION "The number of incoming SIP transactions over the time period."
    ::= { mementoIncomingSIPTransactionsEntry 3 }

mementoIncomingSIPTransactionsSuccesses OBJECT-TYPE
    SYNTAX      Unsigned32
    MAX-ACCESS  read-only
    STATUS      current
    DESCRIPTION "The number of successful incoming SIP transactions over the
                 time period."
    ::= { mementoIncomingSIPTransactionsEntry 4 }

mementoIncomingSIPTransactionsFailures OBJECT-TYPE
    SYNTAX      Unsigned32
    MAX-ACCESS  read-only
    STATUS      current
    DESCRIPTION "The number of failed incoming SIP transactions over the
                 time period. Note that 3xx responses are counted as
                 transaction failures."
    ::= { mementoIncomingSIPTransactionsEntry 5 }

mementoIncomingSIPTransactionsSuccessPercent OBJECT-TYPE
    SYNTAX      Unsigned32
    UNITS       "/ 10000 %"
    MAX-ACCESS  read-only
    STATUS      current
    DESCRIPTION "The percentage of incoming SIP transactions over the
                 period that were successful. Reported in units of ten
                 thousandths of a percentage point. When there are zero
                 attempts made, the value will be 1000000 to represent 100%."
    ::= { mementoIncomingSIPTransactionsEntry 6 }

mementoOutgoingSIPTransactionsTable OBJECT-TYPE
    SYNTAX SEQUENCE OF MementoOutgoingSIPTransactionsEntry
    MAX-ACCESS not-accessible
    STATUS current
    DESCRIPTION "Counts the number of attempts, successes and failures
                 of outgoing SIP transactions for Memento, and (for
                 convenience) provides the percentage of attempts that were
                 successful. Note that CANCEL transactions are not currently
                 tracked in this table."
    ::= { mementoSIP 5 }

mementoOutgoingSIPTransactionsEntry OBJECT-TYPE
    SYNTAX      MementoOutgoingSIPTransactionsEntry
    MAX-ACCESS  not-accessible
    STATUS      current
    DESCRIPTION "The number of attempts, successes and failures for
                 outgoing SIP transactions for Memento, and the percentage
                 of attempts that were successful."
    INDEX       { mementoOutgoingSIPTransactionsTimeScope,
                  mementoOutgoingSIPTransactionsRequestScope }
    ::= { mementoOutgoingSIPTransactionsTable 1 }

MementoOutgoingSIPTransactionsEntry ::= SEQUENCE
{
  mementoOutgoingSIPTransactionsTimeScope      INTEGER,
  mementoOutgoingSIPTransactionsRequestScope   INTEGER,
  mementoOutgoingSIPTransactionsAttempts       Unsigned32,
  mementoOutgoingSIPTransactionsSuccesses      Unsigned32,
  mementoOutgoingSIPTransactionsFailures       Unsigned32,
  mementoOutgoingSIPTransactionsSuccessPercent Unsigned32
}

mementoOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { mementoOutgoingSIPTransactionsEntry 1 }

mementoOutgoingSIPTransactionsRequestScope OBJECT-TYPE
    SYNTAX      RequestType
    MAX-ACCESS  not-accessible
    STATUS      current
    DESCRIPTION "The method type of the outgoing transaction."
    ::= { mementoOutgoingSIPTransactionsEntry 2 }

mementoOutgoingSIPTransactionsAttempts OBJECT-TYPE
    SYNTAX      Unsigned32
    MAX-ACCESS  read-only
    STATUS      current
    DESCRIPTION "The number of outgoing SIP transactions over the time period."
    ::= { mementoOutgoingSIPTransactionsEntry 3 }

mementoOutgoingSIPTransactionsSuccesses OBJECT-TYPE
    SYNTAX      Unsigned32
    MAX-ACCESS  read-only
    STATUS      current
    DESCRIPTION "The number of successful outgoing SIP transactions over the
                 time period."
    ::= { mementoOutgoingSIPTransactionsEntry 4 }

mementoOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { mementoOutgoingSIPTransactionsEntry 5 }

mementoOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { mementoOutgoingSIPTransactionsEntry 6 }

mementoHTTP OBJECT IDENTIFIER ::= { memento 2 }

mementoHTTPRequestTable OBJECT-TYPE
    SYNTAX SEQUENCE OF MementoHTTPRequestEntry
    MAX-ACCESS  not-accessible
    STATUS      current
    DESCRIPTION "Counts of HTTP requests and their outcomes for the given
                 period"
    ::= { mementoHTTP 1 }

mementoHTTPRequestEntry OBJECT-TYPE
    SYNTAX      MementoHTTPRequestEntry
    MAX-ACCESS  not-accessible
    STATUS      current
    DESCRIPTION "Counts of HTTP requests and their outcomes"
    INDEX       { mementoHTTPRequestScope }
    ::= { mementoHTTPRequestTable 1 }

MementoHTTPRequestEntry ::= SEQUENCE
{
    mementoHTTPRequestScope            INTEGER,
    mementoHTTPRequestCount            Unsigned32,
    mementoHTTPRejectedDueToOverload   Unsigned32
}

mementoHTTPRequestScope OBJECT-TYPE
    SYNTAX      INTEGER {
                  scopePrevious5SecondPeriod(1)
                }
    MAX-ACCESS  not-accessible
    STATUS      current
    DESCRIPTION "The period over which the statistics were collected."
    ::= { mementoHTTPRequestEntry 1 }

mementoHTTPRequestCount OBJECT-TYPE
    SYNTAX      Unsigned32
    MAX-ACCESS  read-only
    STATUS      current
    DESCRIPTION "The total number of HTTP requests received."
    ::= { mementoHTTPRequestEntry 2 }

mementoHTTPRejectedDueToOverload OBJECT-TYPE
    SYNTAX      Unsigned32
    MAX-ACCESS  read-only
    STATUS      current
    DESCRIPTION "The total number of HTTP requests rejected due to overload."
    ::= { mementoHTTPRequestEntry 3 }

mementoHTTPRequestLatencyTable OBJECT-TYPE
    SYNTAX SEQUENCE OF MementoHTTPRequestLatencyEntry
    MAX-ACCESS not-accessible
    STATUS current
    DESCRIPTION "Latency of HTTP call record retrieval requests over the given
                 period.  Latency measured in microseconds"
    ::= { mementoHTTP 2 }

mementoHTTPRequestLatencyEntry OBJECT-TYPE
    SYNTAX      MementoHTTPRequestLatencyEntry
    MAX-ACCESS  not-accessible
    STATUS      current
    DESCRIPTION "The average, variance, LWM and HWM of HTTP call retrieval latency"
    INDEX       { mementoHTTPRequestLatencyScope }
    ::= { mementoHTTPRequestLatencyTable 1 }

MementoHTTPRequestLatencyEntry ::= SEQUENCE
{
  mementoHTTPRequestLatencyScope          INTEGER,
  mementoHTTPRequestLatencyAverage        Unsigned32,
  mementoHTTPRequestLatencyVariance       Unsigned32,
  mementoHTTPRequestLatencyHWM            Unsigned32,
  mementoHTTPRequestLatencyLWM            Unsigned32,
  mementoHTTPRequestLatencyCount          Unsigned32
}

mementoHTTPRequestLatencyScope OBJECT-TYPE
    SYNTAX      INTEGER {
                  scopePrevious5SecondPeriod(1)
                }
    MAX-ACCESS  not-accessible
    STATUS      current
    DESCRIPTION "The period over which the statistics were collected."
    ::= { mementoHTTPRequestLatencyEntry 1 }

mementoHTTPRequestLatencyAverage OBJECT-TYPE
    SYNTAX      Unsigned32
    MAX-ACCESS  read-only
    STATUS      current
    DESCRIPTION "The average latency over the period."
    ::= { mementoHTTPRequestLatencyEntry 2 }

mementoHTTPRequestLatencyVariance OBJECT-TYPE
    SYNTAX      Unsigned32
    MAX-ACCESS  read-only
    STATUS      current
    DESCRIPTION "The variance of the latency over the period."
    ::= { mementoHTTPRequestLatencyEntry 3 }

mementoHTTPRequestLatencyHWM OBJECT-TYPE
    SYNTAX      Unsigned32
    MAX-ACCESS  read-only
    STATUS      current
    DESCRIPTION "The highest latency over the period."
    ::= { mementoHTTPRequestLatencyEntry 4 }

mementoHTTPRequestLatencyLWM OBJECT-TYPE
    SYNTAX      Unsigned32
    MAX-ACCESS  read-only
    STATUS      current
    DESCRIPTION "The lowest latency over the period."
    ::= { mementoHTTPRequestLatencyEntry 5 }

mementoHTTPRequestLatencyCount OBJECT-TYPE
    SYNTAX      Unsigned32
    MAX-ACCESS  read-only
    STATUS      current
    DESCRIPTION "The total requests over the period."
    ::= { mementoHTTPRequestLatencyEntry 6 }

mementoHTTPCassandraReadLatencyTable OBJECT-TYPE
    SYNTAX SEQUENCE OF MementoHTTPCassandraReadLatencyEntry
    MAX-ACCESS not-accessible
    STATUS current
    DESCRIPTION "The average, variance, LWM and HWM of Cassandra database read
                 latency reported by the HTTP component.  Latency measured in
                 microseconds"
    ::= { mementoHTTP 3 }

mementoHTTPCassandraReadLatencyEntry OBJECT-TYPE
    SYNTAX      MementoHTTPCassandraReadLatencyEntry
    MAX-ACCESS  not-accessible
    STATUS      current
    DESCRIPTION "The average, variance, LWM and HWM of Cassandra database read
                 latency reported by the HTTP component."
    INDEX       { mementoHTTPCassandraReadLatencyScope }
    ::= { mementoHTTPCassandraReadLatencyTable 1 }

MementoHTTPCassandraReadLatencyEntry ::= SEQUENCE
{
  mementoHTTPCassandraReadLatencyScope          INTEGER,
  mementoHTTPCassandraReadLatencyAverage        Unsigned32,
  mementoHTTPCassandraReadLatencyVariance       Unsigned32,
  mementoHTTPCassandraReadLatencyHWM            Unsigned32,
  mementoHTTPCassandraReadLatencyLWM            Unsigned32,
  mementoHTTPCassandraReadLatencyCount          Unsigned32
}

mementoHTTPCassandraReadLatencyScope OBJECT-TYPE
    SYNTAX      INTEGER {
                  scopePrevious5SecondPeriod(1)
                }
    MAX-ACCESS  not-accessible
    STATUS      current
    DESCRIPTION "The period over which the statistics were collected."
    ::= { mementoHTTPCassandraReadLatencyEntry 1 }

mementoHTTPCassandraReadLatencyAverage OBJECT-TYPE
    SYNTAX      Unsigned32
    MAX-ACCESS  read-only
    STATUS      current
    DESCRIPTION "The average latency over the period."
    ::= { mementoHTTPCassandraReadLatencyEntry 2 }

mementoHTTPCassandraReadLatencyVariance OBJECT-TYPE
    SYNTAX      Unsigned32
    MAX-ACCESS  read-only
    STATUS      current
    DESCRIPTION "The variance of the latency over the period."
    ::= { mementoHTTPCassandraReadLatencyEntry 3 }

mementoHTTPCassandraReadLatencyHWM OBJECT-TYPE
    SYNTAX      Unsigned32
    MAX-ACCESS  read-only
    STATUS      current
    DESCRIPTION "The highest latency over the period."
    ::= { mementoHTTPCassandraReadLatencyEntry 4 }

mementoHTTPCassandraReadLatencyLWM OBJECT-TYPE
    SYNTAX      Unsigned32
    MAX-ACCESS  read-only
    STATUS      current
    DESCRIPTION "The lowest latency over the period."
    ::= { mementoHTTPCassandraReadLatencyEntry 5 }

mementoHTTPCassandraReadLatencyCount OBJECT-TYPE
    SYNTAX      Unsigned32
    MAX-ACCESS  read-only
    STATUS      current
    DESCRIPTION "The total number of reads over the period."
    ::= { mementoHTTPCassandraReadLatencyEntry 6 }

mementoRetrievedCallRecordSizeTable OBJECT-TYPE
    SYNTAX SEQUENCE OF MementoRetrievedCallRecordSizeEntry
    MAX-ACCESS not-accessible
    STATUS current
    DESCRIPTION "Average, variance, HWM and LWM of the size (in kB) of call records
                 retrieved from the store."
    ::= { mementoHTTP 4 }

mementoRetrievedCallRecordSizeEntry OBJECT-TYPE
    SYNTAX      MementoRetrievedCallRecordSizeEntry
    MAX-ACCESS  not-accessible
    STATUS      current
    DESCRIPTION "Average, variance, HWM and LWM of the size (in kB) of call records
                 retrieved from the store."
    INDEX       { mementoRetrievedCallRecordSizeScope }
    ::= { mementoRetrievedCallRecordSizeTable 1 }

MementoRetrievedCallRecordSizeEntry ::= SEQUENCE
{
  mementoRetrievedCallRecordSizeScope          INTEGER,
  mementoRetrievedCallRecordSizeAverage        Unsigned32,
  mementoRetrievedCallRecordSizeVariance       Unsigned32,
  mementoRetrievedCallRecordSizeHWM            Unsigned32,
  mementoRetrievedCallRecordSizeLWM            Unsigned32,
  mementoRetrievedCallRecordSizeCount          Unsigned32
}

mementoRetrievedCallRecordSizeScope OBJECT-TYPE
    SYNTAX      INTEGER {
                  scopePrevious5SecondPeriod(1)
                }
    MAX-ACCESS  not-accessible
    STATUS      current
    DESCRIPTION "The period over which the statistics were collected."
    ::= { mementoRetrievedCallRecordSizeEntry 1 }

mementoRetrievedCallRecordSizeAverage OBJECT-TYPE
    SYNTAX      Unsigned32
    MAX-ACCESS  read-only
    STATUS      current
    DESCRIPTION "The average size over the period."
    ::= { mementoRetrievedCallRecordSizeEntry 2 }

mementoRetrievedCallRecordSizeVariance OBJECT-TYPE
    SYNTAX      Unsigned32
    MAX-ACCESS  read-only
    STATUS      current
    DESCRIPTION "The variance of the size over the period."
    ::= { mementoRetrievedCallRecordSizeEntry 3 }

mementoRetrievedCallRecordSizeHWM OBJECT-TYPE
    SYNTAX      Unsigned32
    MAX-ACCESS  read-only
    STATUS      current
    DESCRIPTION "The highest size over the period."
    ::= { mementoRetrievedCallRecordSizeEntry 4 }

mementoRetrievedCallRecordSizeLWM OBJECT-TYPE
    SYNTAX      Unsigned32
    MAX-ACCESS  read-only
    STATUS      current
    DESCRIPTION "The lowest size over the period."
    ::= { mementoRetrievedCallRecordSizeEntry 5 }

mementoRetrievedCallRecordSizeCount OBJECT-TYPE
    SYNTAX      Unsigned32
    MAX-ACCESS  read-only
    STATUS      current
    DESCRIPTION "The total number of call lists retrieved over the period."
    ::= { mementoRetrievedCallRecordSizeEntry 6 }

mementoRetrievedCallRecordLengthTable OBJECT-TYPE
    SYNTAX SEQUENCE OF MementoRetrievedCallRecordLengthEntry
    MAX-ACCESS not-accessible
    STATUS current
    DESCRIPTION "Average, variance, HWM and LWM of the length (# of records) of call
                 records retrieved from the store."
    ::= { mementoHTTP 5 }

mementoRetrievedCallRecordLengthEntry OBJECT-TYPE
    SYNTAX      MementoRetrievedCallRecordLengthEntry
    MAX-ACCESS  not-accessible
    STATUS      current
    DESCRIPTION "Average, variance, HWM and LWM of the length (# of records) of call
                 records retrieved from the store."
    INDEX       { mementoRetrievedCallRecordLengthScope }
    ::= { mementoRetrievedCallRecordLengthTable 1 }

MementoRetrievedCallRecordLengthEntry ::= SEQUENCE
{
  mementoRetrievedCallRecordLengthScope          INTEGER,
  mementoRetrievedCallRecordLengthAverage        Unsigned32,
  mementoRetrievedCallRecordLengthVariance       Unsigned32,
  mementoRetrievedCallRecordLengthHWM            Unsigned32,
  mementoRetrievedCallRecordLengthLWM            Unsigned32,
  mementoRetrievedCallRecordLengthCount          Unsigned32
}

mementoRetrievedCallRecordLengthScope OBJECT-TYPE
    SYNTAX      INTEGER {
                  scopePrevious5SecondPeriod(1)
                }
    MAX-ACCESS  not-accessible
    STATUS      current
    DESCRIPTION "The period over which the statistics were collected."
    ::= { mementoRetrievedCallRecordLengthEntry 1 }

mementoRetrievedCallRecordLengthAverage OBJECT-TYPE
    SYNTAX      Unsigned32
    MAX-ACCESS  read-only
    STATUS      current
    DESCRIPTION "The average latency over the period."
    ::= { mementoRetrievedCallRecordLengthEntry 2 }

mementoRetrievedCallRecordLengthVariance OBJECT-TYPE
    SYNTAX      Unsigned32
    MAX-ACCESS  read-only
    STATUS      current
    DESCRIPTION "The variance of the latency over the period."
    ::= { mementoRetrievedCallRecordLengthEntry 3 }

mementoRetrievedCallRecordLengthHWM OBJECT-TYPE
    SYNTAX      Unsigned32
    MAX-ACCESS  read-only
    STATUS      current
    DESCRIPTION "The highest latency over the period."
    ::= { mementoRetrievedCallRecordLengthEntry 4 }

mementoRetrievedCallRecordLengthLWM OBJECT-TYPE
    SYNTAX      Unsigned32
    MAX-ACCESS  read-only
    STATUS      current
    DESCRIPTION "The lowest latency over the period."
    ::= { mementoRetrievedCallRecordLengthEntry 5 }

mementoRetrievedCallRecordLengthCount OBJECT-TYPE
    SYNTAX      Unsigned32
    MAX-ACCESS  read-only
    STATUS      current
    DESCRIPTION "The total number of call lists retrieved over the period."
    ::= { mementoRetrievedCallRecordLengthEntry 6 }

mementoAuthProxy OBJECT IDENTIFIER ::= { memento 3 }

mementoConnectedHomesteadsTable OBJECT-TYPE
    SYNTAX SEQUENCE OF MementoConnectedHomesteadsEntry
    MAX-ACCESS not-accessible
    STATUS current
    DESCRIPTION "Statistics for each connected upstream Homestead node"
    ::= { mementoAuthProxy 1 }

mementoConnectedHomesteadsEntry OBJECT-TYPE
    SYNTAX MementoConnectedHomesteadsEntry
    MAX-ACCESS not-accessible
    STATUS current
    DESCRIPTION "Statistics for a single connected upstream Homestead"
    INDEX { mementoHomesteadInetAddrType,
            mementoHomesteadInetAddr      }
    ::= { mementoConnectedHomesteadsTable 1 }

MementoConnectedHomesteadsEntry ::= SEQUENCE
{
  mementoHomesteadInetAddrType    InetAddressType,
  mementoHomesteadInetAddr        InetAddress,
  mementoHomesteadConnectionCount Unsigned32
}

mementoHomesteadInetAddrType OBJECT-TYPE
    SYNTAX      InetAddressType
    MAX-ACCESS  not-accessible
    STATUS      current
    DESCRIPTION "Inet address type of the upstream Homestead"
    ::= { mementoConnectedHomesteadsEntry 1 }

mementoHomesteadInetAddr OBJECT-TYPE
    SYNTAX      InetAddress (SIZE (1..16))
    MAX-ACCESS  not-accessible
    STATUS      current
    DESCRIPTION "Inet address of the upstream Homestead"
    ::= { mementoConnectedHomesteadsEntry 2 }

mementoHomesteadConnectionCount OBJECT-TYPE
    SYNTAX      Unsigned32
    MAX-ACCESS  read-only
    STATUS      current
    DESCRIPTION "Current count of TCP connections from Memento to the
                 Homestead node, may include connections in setting-
                 up state"
    ::= { mementoConnectedHomesteadsEntry 3 }

mementoAuthAttemptTable OBJECT-TYPE
    SYNTAX SEQUENCE OF MementoAuthAttemptEntry
    MAX-ACCESS not-accessible
    STATUS current
    DESCRIPTION "Counts of authentication attempts over the given period."
    ::= { mementoAuthProxy 2 }

mementoAuthAttemptEntry OBJECT-TYPE
    SYNTAX      MementoAuthAttemptEntry
    MAX-ACCESS  not-accessible
    STATUS      current
    DESCRIPTION "Counts of authentication attempts over the given period."
    INDEX       { mementoAuthAttemptScope }
    ::= { mementoAuthAttemptTable 1 }

MementoAuthAttemptEntry ::= SEQUENCE
{
  mementoAuthAttemptScope          INTEGER,
  mementoAuthChallengeCount        Unsigned32,
  mementoAuthAttemptCount          Unsigned32,
  mementoAuthSuccessCount          Unsigned32,
  mementoAuthFailureCount          Unsigned32,
  mementoAuthStaleCount            Unsigned32
}

mementoAuthAttemptScope OBJECT-TYPE
    SYNTAX      INTEGER {
                  scopePrevious5SecondPeriod(1)
                }
    MAX-ACCESS  not-accessible
    STATUS      current
    DESCRIPTION "The period over which the statistics were collected."
    ::= { mementoAuthAttemptEntry 1 }

mementoAuthChallengeCount OBJECT-TYPE
    SYNTAX      Unsigned32
    MAX-ACCESS  read-only
    STATUS      current
    DESCRIPTION "The count of authentication challenges requested."
    ::= { mementoAuthAttemptEntry 2 }

mementoAuthAttemptCount OBJECT-TYPE
    SYNTAX      Unsigned32
    MAX-ACCESS  read-only
    STATUS      current
    DESCRIPTION "The count of authentication attempts."
    ::= { mementoAuthAttemptEntry 3 }

mementoAuthSuccessCount OBJECT-TYPE
    SYNTAX      Unsigned32
    MAX-ACCESS  read-only
    STATUS      current
    DESCRIPTION "The count of successful authentications."
    ::= { mementoAuthAttemptEntry 4 }

mementoAuthFailureCount OBJECT-TYPE
    SYNTAX      Unsigned32
    MAX-ACCESS  read-only
    STATUS      current
    DESCRIPTION "The count of authentication failures due to incorrect credentials."
    ::= { mementoAuthAttemptEntry 5 }

mementoAuthStaleCount OBJECT-TYPE
    SYNTAX      Unsigned32
    MAX-ACCESS  read-only
    STATUS      current
    DESCRIPTION "The count of authentication failures due to stale challenges."
    ::= { mementoAuthAttemptEntry 6 }

mementoDiskUsage OBJECT IDENTIFIER::= { memento 4 }

mementoDatabaseDiskUsage OBJECT-TYPE
    SYNTAX      Unsigned32
    MAX-ACCESS  read-only
    STATUS      current
    DESCRIPTION "Current Memento database disk usage."
    ::= { mementoDiskUsage 1 }

mementoGroup OBJECT-GROUP
    OBJECTS {
        mementoCompletedCallsRecorded,
        mementoFailedCallsRecorded,
        mementoCallsNotRecordedDueToOverload,
        mementoHTTPRequestCount,
        mementoHTTPRejectedDueToOverload,
        mementoHTTPRequestLatencyAverage,
        mementoHTTPRequestLatencyVariance,
        mementoHTTPRequestLatencyHWM,
        mementoHTTPRequestLatencyLWM,
        mementoHTTPRequestLatencyCount,
        mementoSIPCassandraReadLatencyAverage,
        mementoSIPCassandraReadLatencyVariance,
        mementoSIPCassandraReadLatencyHWM,
        mementoSIPCassandraReadLatencyLWM,
        mementoSIPCassandraReadLatencyCount,
        mementoSIPCassandraWriteLatencyAverage,
        mementoSIPCassandraWriteLatencyVariance,
        mementoSIPCassandraWriteLatencyHWM,
        mementoSIPCassandraWriteLatencyLWM,
        mementoSIPCassandraWriteLatencyCount,
        mementoHTTPCassandraReadLatencyAverage,
        mementoHTTPCassandraReadLatencyVariance,
        mementoHTTPCassandraReadLatencyHWM,
        mementoHTTPCassandraReadLatencyLWM,
        mementoHTTPCassandraReadLatencyCount,
        mementoRetrievedCallRecordSizeAverage,
        mementoRetrievedCallRecordSizeVariance,
        mementoRetrievedCallRecordSizeHWM,
        mementoRetrievedCallRecordSizeLWM,
        mementoRetrievedCallRecordSizeCount,
        mementoRetrievedCallRecordLengthAverage,
        mementoRetrievedCallRecordLengthVariance,
        mementoRetrievedCallRecordLengthHWM,
        mementoRetrievedCallRecordLengthLWM,
        mementoRetrievedCallRecordLengthCount,
        mementoHomesteadConnectionCount,
        mementoAuthChallengeCount,
        mementoAuthAttemptCount,
        mementoAuthSuccessCount,
        mementoAuthFailureCount,
        mementoAuthStaleCount,
        mementoDatabaseDiskUsage,
        mementoIncomingSIPTransactionsAttempts,
        mementoIncomingSIPTransactionsSuccesses,
        mementoIncomingSIPTransactionsFailures,
        mementoIncomingSIPTransactionsSuccessPercent,
        mementoOutgoingSIPTransactionsAttempts,
        mementoOutgoingSIPTransactionsSuccesses,
        mementoOutgoingSIPTransactionsFailures,
        mementoOutgoingSIPTransactionsSuccessPercent
    }
    STATUS      current
    DESCRIPTION "Statistics exposed by Memento"
    ::= { projectClearwaterObjectGroups 5 }

-- Gemini Entries

geminiIncomingSIPTransactionsTable OBJECT-TYPE
    SYNTAX SEQUENCE OF GeminiIncomingSIPTransactionsEntry
    MAX-ACCESS not-accessible
    STATUS current
    DESCRIPTION "Counts the number of attempts, successes and failures
                 of incoming SIP transactions for Gemini, and (for
                 convenience) provides the percentage of attempts that were
                 successful. Note that CANCEL transactions are not currently
                 tracked in this table."
    ::= { gemini 1 }

geminiIncomingSIPTransactionsEntry OBJECT-TYPE
    SYNTAX      GeminiIncomingSIPTransactionsEntry
    MAX-ACCESS  not-accessible
    STATUS      current
    DESCRIPTION "The number of attempts, successes and failures for
                 incoming SIP transactions for Gemini, and the percentage
                 of attempts that were successful."
    INDEX       { geminiIncomingSIPTransactionsTimeScope,
                  geminiIncomingSIPTransactionsRequestScope }
    ::= { geminiIncomingSIPTransactionsTable 1 }

GeminiIncomingSIPTransactionsEntry ::= SEQUENCE
{
  geminiIncomingSIPTransactionsTimeScope      INTEGER,
  geminiIncomingSIPTransactionsRequestScope   INTEGER,
  geminiIncomingSIPTransactionsAttempts       Unsigned32,
  geminiIncomingSIPTransactionsSuccesses      Unsigned32,
  geminiIncomingSIPTransactionsFailures       Unsigned32,
  geminiIncomingSIPTransactionsSuccessPercent Unsigned32
}

geminiIncomingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { geminiIncomingSIPTransactionsEntry 1 }

geminiIncomingSIPTransactionsRequestScope OBJECT-TYPE
    SYNTAX      RequestType
    MAX-ACCESS  not-accessible
    STATUS      current
    DESCRIPTION "The method type of the incoming transaction."
    ::= { geminiIncomingSIPTransactionsEntry 2 }

geminiIncomingSIPTransactionsAttempts OBJECT-TYPE
    SYNTAX      Unsigned32
    MAX-ACCESS  read-only
    STATUS      current
    DESCRIPTION "The number of incoming SIP transactions over the time period."
    ::= { geminiIncomingSIPTransactionsEntry 3 }

geminiIncomingSIPTransactionsSuccesses OBJECT-TYPE
    SYNTAX      Unsigned32
    MAX-ACCESS  read-only
    STATUS      current
    DESCRIPTION "The number of successful incoming SIP transactions over the
                 time period."
    ::= { geminiIncomingSIPTransactionsEntry 4 }

geminiIncomingSIPTransactionsFailures OBJECT-TYPE
    SYNTAX      Unsigned32
    MAX-ACCESS  read-only
    STATUS      current
    DESCRIPTION "The number of failed incoming SIP transactions over the
                 time period. Note that 3xx responses are counted as
                 transaction failures."
    ::= { geminiIncomingSIPTransactionsEntry 5 }

geminiIncomingSIPTransactionsSuccessPercent OBJECT-TYPE
    SYNTAX      Unsigned32
    UNITS       "/ 10000 %"
    MAX-ACCESS  read-only
    STATUS      current
    DESCRIPTION "The percentage of incoming SIP transactions over the
                 period that were successful. Reported in units of ten
                 thousandths of a percentage point. When there are zero
                 attempts made, the value will be 1000000 to represent 100%."
    ::= { geminiIncomingSIPTransactionsEntry 6 }

geminiOutgoingSIPTransactionsTable OBJECT-TYPE
    SYNTAX SEQUENCE OF GeminiOutgoingSIPTransactionsEntry
    MAX-ACCESS not-accessible
    STATUS current
    DESCRIPTION "Counts the number of attempts, successes and failures
                 of outgoing SIP transactions for Gemini, and (for
                 convenience) provides the percentage of attempts that were
                 successful. Note that CANCEL transactions are not currently
                 tracked in this table."
    ::= { gemini 2 }

geminiOutgoingSIPTransactionsEntry OBJECT-TYPE
    SYNTAX      GeminiOutgoingSIPTransactionsEntry
    MAX-ACCESS  not-accessible
    STATUS      current
    DESCRIPTION "The number of attempts, successes and failures for
                 outgoing SIP transactions for Gemini, and the percentage
                 of attempts that were successful."
    INDEX       { geminiOutgoingSIPTransactionsTimeScope,
                  geminiOutgoingSIPTransactionsRequestScope }
    ::= { geminiOutgoingSIPTransactionsTable 1 }

GeminiOutgoingSIPTransactionsEntry ::= SEQUENCE
{
  geminiOutgoingSIPTransactionsTimeScope      INTEGER,
  geminiOutgoingSIPTransactionsRequestScope   INTEGER,
  geminiOutgoingSIPTransactionsAttempts       Unsigned32,
  geminiOutgoingSIPTransactionsSuccesses      Unsigned32,
  geminiOutgoingSIPTransactionsFailures       Unsigned32,
  geminiOutgoingSIPTransactionsSuccessPercent Unsigned32
}

geminiOutgoingSIPTransactionsTimeScope OBJECT-TYPE
    SYNTAX      INTEGER {
                  scopePrevious5SecondPeriod(1),
                  scopeCurrent5MinutePeriod(2),
                  scopePrevious5MinutePeriod(3)
                }
    MAX-ACCESS  not-accessible
    STATUS      current
    DESCRIPTION "The period over which the statistics were collected."
    ::= { geminiOutgoingSIPTransactionsEntry 1 }

geminiOutgoingSIPTransactionsRequestScope OBJECT-TYPE
    SYNTAX      RequestType
    MAX-ACCESS  not-accessible
    STATUS      current
    DESCRIPTION "The method type of the outgoing transaction."
    ::= { geminiOutgoingSIPTransactionsEntry 2 }

geminiOutgoingSIPTransactionsAttempts OBJECT-TYPE
    SYNTAX      Unsigned32
    MAX-ACCESS  read-only
    STATUS      current
    DESCRIPTION "The number of outgoing SIP transactions over the time period."
    ::= { geminiOutgoingSIPTransactionsEntry 3 }

geminiOutgoingSIPTransactionsSuccesses OBJECT-TYPE
    SYNTAX      Unsigned32
    MAX-ACCESS  read-only
    STATUS      current
    DESCRIPTION "The number of successful outgoing SIP transactions over the
                 time period."
    ::= { geminiOutgoingSIPTransactionsEntry 4 }

geminiOutgoingSIPTransactionsFailures OBJECT-TYPE
    SYNTAX      Unsigned32
    MAX-ACCESS  read-only
    STATUS      current
    DESCRIPTION "The number of failed outgoing SIP transactions over the
                 time period. Note that 3xx responses are counted as
                 transaction failures."
    ::= { geminiOutgoingSIPTransactionsEntry 5 }

geminiOutgoingSIPTransactionsSuccessPercent OBJECT-TYPE
    SYNTAX      Unsigned32
    UNITS       "/ 10000 %"
    MAX-ACCESS  read-only
    STATUS      current
    DESCRIPTION "The percentage of outgoing SIP transactions over the
                 period that were successful. Reported in units of ten
                 thousandths of a percentage point. When there are zero
                 attempts made, the value will be 1000000 to represent 100%."
    ::= { geminiOutgoingSIPTransactionsEntry 6 }

geminiGroup OBJECT-GROUP
    OBJECTS {
      geminiIncomingSIPTransactionsAttempts,
      geminiIncomingSIPTransactionsSuccesses,
      geminiIncomingSIPTransactionsFailures,
      geminiIncomingSIPTransactionsSuccessPercent,
      geminiOutgoingSIPTransactionsAttempts,
      geminiOutgoingSIPTransactionsSuccesses,
      geminiOutgoingSIPTransactionsFailures,
      geminiOutgoingSIPTransactionsSuccessPercent
    }
    STATUS    current
    DESCRIPTION "Statistics exposed by Gemini"
    ::= { projectClearwaterObjectGroups 11  }

END
